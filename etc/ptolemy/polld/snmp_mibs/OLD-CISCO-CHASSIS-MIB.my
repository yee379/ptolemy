-- *****************************************************************
-- OLD-CISCO-CHASSIS-MIB.my:  Cisco Chassis MIB file
--
--
-- May 1994, Jeffrey T. Johnson
--
-- Copyright (c) 1994-2001, 2002, 2003, 2004, 2005 by cisco Systems, Inc.
-- All rights reserved.
--
-- NOTE WELL
-- Starting with IOS 12.0, all objects defined in this mib have been
-- deprecated.  They have been replaces with objects defined in the
-- ENTITY-MIB.my document. Management applications should no longer
-- be examining the objects defined in this document.
-- NOTE WELL
-- 
-- *****************************************************************
--
--
               OLD-CISCO-CHASSIS-MIB DEFINITIONS ::= BEGIN

               IMPORTS
                    TimeTicks
                        FROM RFC1155-SMI
                    OBJECT-TYPE
			FROM RFC-1212
                    DisplayString
			FROM RFC1213-MIB
		    temporary
			FROM CISCO-SMI;
          
               chassis             OBJECT IDENTIFIER ::= { temporary 6 }

               -- Temporary Chassis Section


               -- (not the same as the IETF Chassis MIB)

          -- This group is present in all products.

               chassisType OBJECT-TYPE
                   SYNTAX  INTEGER {
			unknown(1)
			,multibus(2)
			,agsplus(3)
			,igs(4)
			,c2000(5)
			,c3000(6)
			,c4000(7)
			,c7000(8)
			,cs500(9)
			,c7010(10)
			,c2500(11)
			,c4500(12)
			,c2102(13)
			,c2202(14)
			,c2501(15)
			,c2502(16)
			,c2503(17)
			,c2504(18)
			,c2505(19)
			,c2506(20)
			,c2507(21)
			,c2508(22)
			,c2509(23)
			,c2510(24)
			,c2511(25)
			,c2512(26)
			,c2513(27)
			,c2514(28)
			,c2515(29)
			,c3101(30)
			,c3102(31)
			,c3103(32)
			,c3104(33)
			,c3202(34)
			,c3204(35)
			,accessProRC(36)
			,accessProEC(37)
			,c1000(38)
			,c1003(39)
			,c1004(40)
			,c2516(41)
			,c7507(42)
			,c7513(43)
			,c7506(44)
			,c7505(45)
			,c1005(46)
			,c4700(47)
			,c2517(48)
			,c2518(49)
			,c2519(50)
			,c2520(51)
			,c2521(52)
			,c2522(53)
			,c2523(54)
			,c2524(55)
			,c2525(56)
			,c4700S(57)
			,c7206(58)
			,c3640(59)
			,as5200(60)
			,c1601(61)
			,c1602(62)
			,c1603(63)
			,c1604(64)
			,c7204(65)
			,c3620(66)
			,wsx3011(68)
			,mc3810(69)
			,c1503(72)
			,as5300(73)
			,as2509RJ(74)
			,as2511RJ(75)
			,c2501FRADFX(77)
			,c2501LANFRADFX(78)
			,c2502LANFRADFX(79)
			,wsx5302(80)		
			,c1605(81)
			,c12012(82)
			,c12008(85)
			,ubr7246(86)			-- Universal Broadband Router
			,c2610(87)			-- c2600 with 1 integrated ethernet interface 
			,c2612(88)			-- c2600 with an integrated ethernet and token ring interface
			,c2611(89)			-- c2600 with 2 integrated ethernet interfaces
			,ubr904(90)			-- Cisco Cable Modem (ubr - universal broadband router)
			,c6200(91)			-- Digital Subscriber Line Access Multiplexer(DSLAM) 
			,c3660(92)                      -- Six slot MARS Router
			,c7202(94)                      -- Modular two slot router in the cisco7200 family
			,c2620(95)			-- c2600 platform with an onboard fast ethernet
			,c2621(96)			-- c2600 platform with two onboard fast ethernets
			,rpm(99)			-- Router Processor Module 
			,c1710(100)			-- VPN(Virtual Private Network) Security Router with 1 FastEthernet and 1 Ethernet interface onboard
			,c1720(101)                     
			,c7576(102)			-- Dual Independent RSP platform, 13 slots
			,c1401(103)			-- Router with 1 ethernet and 1 ATM25 interface 
			,c2613(104)			-- c2600 with 1 integrated token ring interface
			,ubr7223(105)			-- Universal Broadband Router
			,c6400Nrp(106)			-- c6400 Network Routing Processor
			,c801(107)			-- Cisco 800 platform with 1 ethernet and 1 BRI/ST 
			,c802(108)			-- Cisco 800 platform with 1 ethernet and 1 BRI U 
			,c803(109)			-- Cisco 800 platform with 1 ethernet 4-port hub, 1 BRI S/T, and 2 POTs 
			,c804(110)			-- Cisco 800 platform with 1 ethernet 4-port hub, 1 BRI U, and 2 POTs 
			,c7206VXR(111)			-- Cisco 7200 platform, VXR series chassis with 6 slots 
			,c7204VXR(112)			-- Cisco 7200 platform, VXR series chassis with 4 slots
			,c1750(113)			-- VoIP (Voice over IP) capable Cisco 1700 platform with 2 WIC/VIC slots and 1 VIC-only slot
			,mgx8850(114)			-- Cisco MGX8850 Multiservice Gigabit Switch with 32 half height slots
			,c805(116)			-- Cisco 800 platform with 1 ethernet and 1 serial WIC 
			,ws-c3508g-xl(117)		-- Cisco Catalyst 3508G-XL switch with 8 GBIC Gigabit ports, can run Standard or Enterprise edition software. 
			,ws-c3512-xl(118)		-- Cisco Catalyst 3512XL switch with 12 10/100BaseTX ports and 2 GBIC Gigabit ports, can run Standard or Enterprise edition software. 
			,ws-c3524-xl(119)		-- Cisco Catalyst 3524XL switch with 24 10/100BaseTX ports and 2 GBIC Gigabit ports, can run Standard or Enterprise edition software.
			,ws-c2908-xl(120)		-- Cisco Catalyst 2900XL series 8 port 10/100BaseTX switch
			,ws-c2916m-xl(121)		-- Cisco Catalyst 2916M-XL switch with 16 10/100BaseTX ports and 2 uplink slots.
			,ws-c2924-xl-v(122)		-- Cisco Catalyst 2924XL switch with 24 autosensing 10/100BaseTX ports; supports port-based VLANs; can run Standard or Enterprise edition software. 
			,ws-c2924c-xl-v(123)		-- Cisco Catalyst 2924C-XL switch with 22 autosensing 10/100BaseTX ports and 2 100BaseFX ports; supports port-based VLANs, can run Standard or Enterprise edition software.
			,ws-c2912-xl(124)		-- Cisco Catalyst 2912XL switch with 12 autosensing 10/100BaseTX ports, can run Standard or Enterprise edition software. 
			,ws-c2924m-xl(125)		-- Cisco Catalyst 2924M-XL switch with 24 autosensing 10/100BaseTX ports and 2 uplink slots, can run Standard or Enterprise edition software.
			,ws-c2912mf-xl(126)		-- Cisco Catalyst 2912MF-XL switch with 12 100BaseFX ports and 2 uplink slots; can only run Enterprise edition software.
			,c1417(128)			-- Cisco 1400 series router with 1 Ethernet and 1 ADSL interface, with 1417 chipset
			,cOpticalRegenerator(129)	-- Cisco Optical Regenerator
			,ws-c2924-xl(130)		-- Cisco Catalyst 2924XL with 24 10/100BaseTX switch ports; doesn't support port-based VLANs.
			,ws-c2924c-xl(131)		-- Cisco Catalyst 2924C-XL; doesn't support port-based VLANs.
			,ubr924(132)			-- Cisco UBR Cable Modem which is a UBR904 with 2 FXS Voice ports
                        ,ws-x6302-msm(133)              -- Catalyst 6000 or 6500 Series Multilayer Switch Module WS-X6302-MSM that directly interfaces to the switch's backplane to provide layer 3 switching.
			,cat5k-rsfc(134)		-- Router Switching Feature Card for the Catalyst 5000 that is treated as a standalone system by the NMS
			,c7120-quadt1(136)		-- 7120 Series chassis with 2 10/100 FE interfaces, 4 T1/E1 interfaces
			,c7120-t3(137)			-- 7120 Series chassis with 2 10/100 FE interfaces, 1 T3 interface
			,c7120-e3(138)			-- 7120 Series chassis with 2 10/100 FE interfaces, 1 E3 interface
			,c7120-at3(139)			-- 7120 Series chassis with 2 10/100 FE interfaces, 1 T3 ATM interface
			,c7120-ae3(140)			-- 7120 Series chassis with 2 10/100 FE interfaces, 1 E3 ATM interface
			,c7120-smi3(141)		-- 7120 Series chassis with 2 10/100 FE interfaces, 1 OC3SMI ATM interface
			,c7140-dualt3(142)		-- 7140 Series chassis with 2 10/100 FE interfaces, 2 T3 interfaces
			,c7140-duale3(143)		-- 7140 Series chassis with 2 10/100 FE interfaces, 2 E3 interfaces
			,c7140-dualat3(144)		-- 7140 Series chassis with 2 10/100 FE interfaces, 2 T3 ATM interfaces 
			,c7140-dualae3(145)		-- 7140 Series chassis with 2 10/100 FE interfaces, 2 E3 ATM interfaces
			,c7140-dualmm3(146)		-- 7140 Series chassis with 2 10/100 FE interfaces, 2 OC3MM ATM interfaces
			,c12016(150)			-- Cisco 12000 platform with 16 slots
			,c7140-octt1(152)		-- 7140 Series chassis with 8 integrated T1/E1 serial ports
			,c7140-dualfe(153)		-- 7140 Series chassis with 2 integrated 10/100 FE interfaces
			,cat3548xl(154)			-- Catalyst 3548XL switch (WS-C3548-XL)
			,cat6006(155)			-- Catalyst 6000 with 6 slots 
			,cat6009(156)			-- Catalyst 6000 with 9 slots 
			,cat6506(157)			-- Catalyst 6000 Plus with 6 slots 
			,cat6509(158)			-- Catalyst 6000 Plus with 9 slots 
			,mc3810-v3(160)			-- Cisco MC3810-V3, capable of data, voice and video.  Supports 2 additional ports than the MC3810-V, used for optional access cards.
			,c7507z(162)			-- Cisco 7507z chassis, Czbus capable, 7 slots
			,c7513z(163)			-- Cisco 7513z chassis, Czbus capable, 13 slots
			,c7507mx(164)			-- Cisco 7507mx chassis, Czbus capable, TDM (Time Division Multiplexing) backplane support, 7 slots
			,c7513mx(165)			-- Cisco 7513mx chassis, Czbus capable, TDM (Time Division Multiplexing) backplane support, 13 slots
			,ubr912-c(166)			-- Cisco uBR912-C Cable Modem with CSU/DSU WIC
			,ubr912-s(167)			-- Cisco uBR912-S Cable Modem with Serial WIC
			,ubr914(168)			-- Cisco uBR914 Cable Modem with removable WIC
			,cat4232-l3(173)	-- Cisco Catalyst 4232-L3 layer 3 line card that is treated as a standalone system by the NMS
			,cOpticalRegeneratorDCPower(174)	-- Cisco Optical Regenerator with DC power supply
			,cva122(180)			--   Cisco CVA122 Cable Voice Adapter (Residential Cable Modem with two Voice Ports)
			,cva124(181)			--   Cisco CVA124 Cable Voice Adapter (Residential Cable Modem with four Voice Ports)
			,as5850(182)			--  High End Dial Access Server
			,mgx8240(185)			-- High Density Circuit Emulation Service Gateway chassis with two shelf controller slots and fifteen Service Modulesfor Private Line Service
			,ubr925(191)		-- Cisco UBR925 Cable Modem/Router with VOIP and hardware accelerated IPSEC
			,ubr10012(192)		-- Cisco uBR10000 platform with 8 broadband slots and 4 WAN slots
			,c12016-8r(194)		-- Teracore ready 8 rail chassis for Cisco 12000 platform
			,c2650(195)		-- c2650 platform with 1 integrated fast ethernet interface
			,c2651(196)		-- c2650 platform with 2 integrated fast ethernet interfaces
			,c1751(202)		-- Digital voice capable Cisco 1700 platform with 2 WIC/VIC slots and 1 VIC-only slot 
			,c626(205)		-- Cisco 600 DSL CPE pltaform with ADSL, DMT issue 1, 25M ATM interface
			,c627(206)		-- Cisco 600 DSL CPE pltaform with ADSL, DMT issue 2, 25M ATM interface
			,c633(207)		-- Cisco 600 DSL CPE platform with SDSL, 2B1Q line coding, serial interface (V.35/X.21)
			,c673(208)		-- Cisco 600 DSL CPE platform with SDSL, 2B1Q line coding, ethernet interface
			,c675(209)		-- Cisco 600 DSL CPE platform with ADSL, CAP, ethernet interface, POTS connector
			,c675e(210)		-- Cisco 600 DSL CPE platform with ADSL, CAP, ethernet interface, universal power supply
			,c676(211)		-- Cisco 600 DSL CPE platform with ADSL, DMT issue 1, ethernet interface
			,c677(212)		-- Cisco 600 DSL CPE platform with ADSL, DMT issue 2, ethernet interface
			,c678(213)		-- Cisco 600 DSL CPE platform with ADSL, CAP/DMT/G.Lite, ethernet interface
			,c3661-ac(214)		-- 1 Fast Ethernet version of c3660 with a AC power supply
			,c3661-dc(215)		-- 1 Fast Ethernet version of c3660 with a DC power supply
			,c3662-ac(216)		-- 2 Fast Ethernet version of c3660 with a AC power supply
			,c3662-dc(217)		-- 2 Fast Ethernet version of c3660 with a DC power supply
			,c3662-ac-co(218)		-- 2 Fast Ethernet version of c3660 with a AC power supply for Telco's
			,c3662-dc-co(219)		-- 2 Fast Ethernet version of c3660 with a DC power supply for Telco's
			,ubr7111(220)			-- Low-end version of the Universal Broadband Router with 1 PA slot, 1 fixed RF line card (MC11C) and integrated upconvertor, designed for hotels, MDUs and smaller cable operators
			,ubr7114(222)			-- Low-end version of the Universal Broadband Router with 1 PA slot, 1 fixed RF line card (MC14C) and integrated upconvertor, designed for hotels, MDUs and smaller cable operators
			,c12010(224)			-- Cisco 12000 platform with 10 slots
			,c8110(225)			-- Cisco 8110 (ATM network termination device) with 3 Line Interface module slots
			,ubr905(227)			-- Cisco uBR905 Cable Modem with hardware accelerated IPSEC
			,c7150-dualfe(231)		-- 7150 Series chassis with 2 integrated 10/100 FE interfaces
			,c7150-octt1(232)		-- 7150 Series chassis with 8 integrated T1/E1 serial ports
			,c7150-dualt3(233)		-- 7150 Series chassis with 2 10/100 FE interfaces, 2 T3 interfaces
			,cvps1110(236)			-- Cisco VLAN Policy Server 1110 manages VLAN-based policies to control user access to a LAN, leveraging existing authentication mechanisms such as Windows Domain Controllers and Novell's NDS. This policy server is part of CiscoWorks2000 User Registration Tool product.
			,ccontentengine(237)		-- Cisco Content Engine Chassis.  The Cisco Content Engine is a Content Networking product that accelerates content delivery, ensuring maximum scalability and availability of content.  The Content Engines offer caching, Content Delivery Network (CDN) services, employee internet management (e.g., URL filtering) and proxy services
			,ciad2420(238)			-- Integrated Access Device 2420 (IAD2420) chassis with Analog (8/16) FXS ports with T1 or ADSL (Asymmetrical Digital Subscriber Line) Uplinks
			,c677i(239)			-- Cisco 600 DSL CPE platform with ASDL, DMT issue 2 over ISDN, ethernet interface
			,c674(240)			-- Cisco 600 DSL CPE platform with G.SHDSL, ethernet interface
			,cdpa7630(241)			-- The Cisco Digital PBX Adapter (DPA) enables the integration of Cisco Call Manager with Octel voice mail systems
			,cat2924-lre-xl(245)		-- Cisco Catalyst c2924XL switch (WS-C2924-LRE-XL) with 24 10BaseS VDSL ports and 4 10/100BaseTX ports
			,cat2912-lre-xl(246)		-- Cisco Catalyst c2912XL switch (WS-C2912-LRE-XL) with 12 10BaseS VDSL ports and 4 10/100BaseTX ports
			,cva122e(247)			-- Cisco CVA122-e Cable Voice Adapter(Residential Cable Modem with two voice ports)- European version 
			,cva124e(248)			-- Cisco CVA124-e Cable Voice Adapter(Residential Cable Modem with four voice ports)- European version
			,curm(249)			-- Universal Router Module for the IGX platform
			,curm2fe(250)			-- Universal router module with 2 Fast Ethernet interfaces for IGX platform
			,curm2fe2v(251)			-- Universal Router Module, with 2 Fast Ethernet ports, and 2 digital voice ports (T1 or E1)
			,c7401VXR(252)			-- Cisco 7400 Family, 1 Slot router
			,cap340(255)			-- Aironet Wireless LAN Access Point 340 series
			,cap350(256)			-- Cisco Wireless LAN Access Point 350 series 
			,cdpa7610(257)			-- The Cisco Digital PBX Adapter (DPA) enables the integration of Cisco Call Manager with Octel voice mail systems
			,c12416(261)			-- Cisco 12000 platform with 16 slots and 10G Fabric card
			,ws-c2948g-l3-dc(262)		-- A fixed-configuration Layer 3 Ethernet switch featuring IP, IPX, and IP mulitcast with 48 10/100BaseTX ports and 2 GBIC Gigabit ports using DC power
			,ws-c4908g-l3-dc(263)		-- A fixed-configuration L3 Ethernet switch featuring IP,IPX and IP multicast with 8 GBIC ports using DC power
			,c12406(264)			-- Cisco 12400 platform with 6 slots
			,pix-firewall506(265)		-- Cisco PIX Firewall 506
			,pix-firewall515(266)		-- Cisco PIX Firewall 515
			,pix-firewall520(267)		-- Cisco PIX Firewall 520
			,pix-firewall525(268)		-- Cisco PIX Firewall 525
			,pix-firewall535(269)		-- Cisco PIX Firewall 535
			,c12410(270)			-- Cisco 12410 platform with 10 slots
			,c811(271)			-- ISDN router for Japan with 1 10BaseT Ethernet port, 1 ISDN BRI(Basic Rate Interface) U, integrated DSU(Data Service Unit)
			,c813(272)			-- ISDN router for Japan with 10 BaseT 4 ports hub , 1 ISDN BRI(Basic Rate Interface) U, integrated DSU(Data Service Unit) and 2 RJ-11
			,c10720(273)			-- IP + Optical Access Router
            ,cMWR1900(274)			-- The Mobile Wireless router is a router targeted at application in a cell site Base Transciever Station (BTS) providing T1/E1 backhaul connections to the aggregation node in Radio Access Networks (RAN)
			,c4224(275)			-- A standalone 24 port powered Ethernet switch, router and voice gateway
			,cWSC6513(276)			-- Catalyst 6000 series chassis with 13 slots 
			,c7603(277)			-- Cisco Internet Router 7600 Series Chassis with 3 slots 
			,c7606(278)			-- Cisco Internet Router 7600 Series Chassis with 6 slots 
			,c7401ASR(279)			-- Cisco 7400 platform, ASR series with 1 slot
			,cVG248(280)			-- Cisco VoIP Voice Gateway for connecting analog telephones fax machines to a Cisco Call Manager based system
			,c1105(281)			-- CiscoWorks network management chassis
			,cCe507(284)			-- Cisco Content Engine Model 507
			,cCe560(285)			-- Cisco Content Engine Model 560
			,cCe590(286)			-- Cisco Content Engine Model 590
			,cCe7320(287)			-- Cisco Content Engine Model 7320
			,c2691(288)			-- One Network Module slot, three WIC slot, two Fast Ethernet port MARS router 
			,c3725(289)			-- Two Network Module slot, three WIC slot, two Fast Ethernet port MARS router 
			,c1760(291)			-- Analog/digital voice capable, 19" rack-mount (1RU) Cisco 1700 platform with 2 WIC/VIC slots and 2 VIC-only slots 
			,pix-firewall501(292)		-- Cisco PIX Firewall 501
			,c2610M(293)			-- c2600M chassis  with 1 integrated ethernet interface
			,c2611M(294)			-- c2600M chassis with 2 integrated ethernet interfaces
			,c12404(298)			-- Cisco 12400 platform with 4 slots
			,c9004(299)			-- Cisco 9000 Chassis
			,cCe507av(307)			-- Cisco Content Engine Model 507-AV
			,cCe560av(308)			-- Cisco Content Engine Model 560-AV
			,cIe2105(309)			-- The Cisco Intelligence Engine 2100 series is a new form of network device that provides intelligent network interface to applications and users
			,c7304(313)			-- Cisco 7300 Chassis
			,cWSC6503(322)			-- Catalyst 6000 series chassis with 3 slots 
			,ccontentengine2636(326)	-- Cisco Content Engine Module for 26xx and 36xx series platforms
			,ccontentengine-dw2636(327)	-- Double Wide Cisco Content Engine Module for 26xx and 36xx series
			,c6400-uac(332)                 -- Cisco 6400 Universal Access Concentrator
			,c2610XM(334)                   -- Cisco 2610XM platform with 1 integrated fast ethernet interfaces with SDRAM
			,c2611XM(335)                   -- Cisco 2611XM platform with 2 integrated fast ethernet interfaces with SDRAM
			,c2620XM(336)                   -- Cisco 2620XM platform with 1 integrated fast ethernet interfaces with SDRAM
			,c2621XM(337)                   -- Cisco 2621XM platform with 2 integrated fast ethernet interfaces with SDRAM
			,c2650XM(338)                   -- Cisco 2650XM platform with 1 integrated fast ethernet interfaces with SDRAM
			,c2651XM(339)                   -- Cisco 2651XM platform with 2 integrated fast ethernet interfaces with SDRAM
			,cat295024sx(350)		-- Cisco Catalyst c2950 switch with 24 10/100 BaseTX ports and 2 fixed 1000Base Multimode fiber (SX) ports (WS-C2950SX-24)
			,as5400-hpx(353) 		-- chassis for cisco As5400HPX
			,c7609(365)			-- 9 slots chassis in Cisco 7600 family
			,cVG200(372)			-- The Cisco VG200 chassis for Voice-over-IP (VoIP) Gateway
			,airap1210(373)			-- 1200 series WLAN Access Point on Cisco IOS platform with 1 10/100TX port, 1 CardBus slot, 1 Mini PCI slot
			,cat375048PS(374)		-- Catalyst 3750 48 10/100 ports with In-Line Power + 2 Gigabit SFP ports fixed configuration Layer 2/Layer 3 Ethernet Stackable Switch.(SFP Small Formfactor Pluggable)
			,c7613(377)			-- Cisco Internet router 7600 Series Chassis with 13 slots 
			,airbr-1410(380)		-- 1410 Series Wireless LAN Bridge on Cisco IOS platform with 1 10/100Tx port and 1 5-GHz radio
			,cWSC6509neba(381)		-- Catalyst 6500 series chassis with 9 slots
			,c1701(384)			-- c1701 is a re-packaging of existing products to create a fixed configuration sku. It has ADSLoPOTs WIC and ISDN BRI (S/T) WIC riveted into it.
			,cat29408TT(385)		-- Catalyst 2940 L2 switch with 8 10/100 copper ports and 1 10/100/1000 copper uplink port.
			,cat29408TF(386)		-- Catalyst 2940 L2 switch with 8 10/100 copper ports, 1 100 FX Uplink port and 1 Gigabit SFP Module slot.
			,airap350ios(394)		-- Cisco Wireless LAN Access Point 350 series on IOS platform with 1 10/100TX port, 1 IEEE 802.11 radio port
			,cat295024-lre-st-997(396)      -- Cisco Catalyst2905 Long Reach Ethernet switch that confirms to ETSI 997 with 24 LRE interfaces, 2 10/100/1000 Small form factor copper interfaces and DC power supply(WS-C2905ST-24-LRE-997)
			,cat6k-sup720(400)		-- Catalyst 6500 Supervisor Module 720 CPU board that is treated as a standalone system by the NMS
			,airbr-1300(404)			-- Cisco Aironet 1300 Series Wireless Bridge with 1 10/100 TX Ethernet port, 1 IEEE 802.11g radio port
			,c2811(413)			-- 2800 Family Router with two integrated fast ethernets and integrated VPN
			,c2821(414)			-- 2800 Family Router with two integrated gigabit ethernets and integrated VPN
			,c2851(415)			-- 2800 Family Router with two integrated gigabit ethernets and integrated VPN
			,cat3750g-16td(420)		-- Cisco Catalyst 3750 switch with 16 gigabit and one 10G ethernet port (WS-C3750G-16TD)
			,cigesm(422)			--  Cisco Systems Intelligent Gigabit Ethernet Switch Module for IBM eServer BladeCenter (OS-CIGESM-18TT-E)
			,c1841(423)			--  1700 Next Generation data only router with 2 slots 
			,c2801(424)			--  1700 Next Generation data only router with 4 slots 
			,cds-x9132-k9(430)		--  DS-X9132-K9 MDS 9132 Chassis
			,cds-x9116-k9(431)		--  DS-X9116-K9 MDS 9116 Chassis
			,cds-c9216i-k9(436)		--  2-Slot MDS fabric switch chassis
			,airap-1130(439)		--  Cisco Aironet 1130 series WLAN Access Point with 1 10/100TX port, dual IEEE 802.11a and 802.11g  radio port
			,c7604(440)			--  Cisco 7604 chassis, a 4-slot chassis. 
-- removed can reuse assignment
			,c371098-hp-001(443)		--  24 port Gigabit Ethernet switch module for HP ProLiant BL p-class server chassis
			,cwlse1130(454)			--  Chassis for Cisco WLSE 1130.
			,cwlse1030(455)			--  Chassis for Cisco WLSE 1030.
			,cids4210(457)			--  Cisco Intrusion Detection System 4210
			,cids4215(458)			--  Cisco Intrusion Detection System 4215
			,cids4235(459)			--  Cisco Intrusion Detection System 4235
			,cids4240(460)			--  Cisco Intrusion Prevention System 4240
			,cids4250(461)			--  Cisco Intrusion Detection System 4250
			,cids4250sx(462)			--  Cisco Intrusion Detection System 4250 with fiber interface
			,cids4250xl(463)			--  Cisco Intrusion Detection System 4250 with accelerator card
			,cids4255(464)			--  Cisco Intrusion Prevention System 4255
			,cWSC6504E(466)			--  Catalyst 6000 series chassis with 4 slots 
			,cfe-6326-k9(468)			-- Cisco File Engine Model FE-6326-K9 
			,dsC9120ClK9(471)			-- DS-C9120-CL-K9  - MDS 9120-CL, 20-Port 4 Gbps Fibre Channel Fabric Switch, Commercial
			,cat6k-msfc2a (481)			-- Multilevel Switching Feature Card Version 2a for Catalyst 6000 that is treated as a standalone system by the NMS
			,cme6340aca (482)			-- DSL Switch 48 port ADSL2/2+, Annex A, AC
			,cme6340dca (483)			-- DSL Switch 48 port ADSL2/2+, Annex A, DC
			,cme6340dcb (484)			-- DSL Switch 48 port ADSL2/2+, Annex B, DC
			,nm-16es-1ge (493)			-- 16 Ports next genaration 10BaseT/100BaseTX EtherSwitch module with 1 GE and Inline Power
			,nm-x-24es-1ge (494)			-- 24 Ports extended next genaration 10BaseT/100BaseTX EtherSwitch module with 1 GE and Inline Power
			,nm-xd-24es-2st (495)			-- 24 Ports extended double-wide next genaration 10BaseT/100BaseTX EtherSwitch module with 2 stacking ports and Inline Power
			,nm-xd-48es-2ge (496)			-- 48 Ports extended double-wide next genaration 10BaseT/100BaseTX EtherSwitch module with 2 GE and Inline Power
			,nm-16es-1ge-no-pwr (497)			-- 16 Ports next genaration 10BaseT/100BaseTX EtherSwitch module with 1 GE
			,nm-xd-24es-2st-no-pwr (498)			-- 24 Ports extended double-wide next genaration 10BaseT/100BaseTX EtherSwitch module with 2 stacking ports
			,nm-xd-48es-2ge-no-pwr (499)			-- 48 Ports extended double-wide next genaration 10BaseT/100BaseTX EtherSwitch module with 2 GE
			,nm-x-24es-1ge-no-pwr (500)			-- 24 Ports extended next genaration 10BaseT/100BaseTX EtherSwitch module with 1 GE
			,cCRS18-linecard (513)			-- Cisco CRS-1 Series 8 slot Line Card Chassis
			,cCRS1-fabric (514)			-- Cisco CRS-1 Series Fabric Card Chassis
			,cids4220 (515)				-- Cisco Intrusion Detection System 4220
			,cids4230 (516)				-- Cisco Intrusion Detection System 4230

		}
                   ACCESS  read-only
                   STATUS  deprecated
                   DESCRIPTION                           "Chassis type."
                   ::= { chassis 1 }

               chassisVersion OBJECT-TYPE
                   SYNTAX  DisplayString
                   ACCESS  read-only
                   STATUS  deprecated
                   DESCRIPTION                           "Chassis hardware revision level, or an empty
                           string if unavailable."
                   ::= { chassis 2 }

               chassisId OBJECT-TYPE
                   SYNTAX  DisplayString
                   ACCESS  read-write
                   STATUS  deprecated
                   DESCRIPTION                           "Unique ID string. Defaults to chassis serial
                           number if available, otherwise empty. Can
                           also be set with 'snmp-server chassis-id'."
                   ::= { chassis 3 }

               romVersion OBJECT-TYPE
                   SYNTAX  DisplayString
                   ACCESS  read-only
                   STATUS  deprecated
                   DESCRIPTION                           "ROM monitor version."
                   ::= { chassis 4 }

               romSysVersion OBJECT-TYPE
                   SYNTAX  DisplayString
                   ACCESS  read-only
                   STATUS  deprecated
                   DESCRIPTION                           "ROM system software version, or an empty
                           string if unavailable."
                   ::= { chassis 5 }

               processorRam OBJECT-TYPE
                   SYNTAX  INTEGER
                   ACCESS  read-only
                   STATUS  deprecated
                   DESCRIPTION                           "Bytes of RAM available to CPU."
                   ::= { chassis 6 }

               nvRAMSize OBJECT-TYPE
                   SYNTAX  INTEGER
                   ACCESS  read-only
                   STATUS  deprecated
                   DESCRIPTION                           "Bytes of non-volatile configuration memory."
                   ::= { chassis 7 }

               nvRAMUsed OBJECT-TYPE
                   SYNTAX  INTEGER
                   ACCESS  read-only
                   STATUS  deprecated
                   DESCRIPTION                           "Bytes of non-volatile configuration memory
                           in use."
                   ::= { chassis 8 }

               configRegister OBJECT-TYPE
                   SYNTAX  INTEGER
                   ACCESS  read-only
                   STATUS  deprecated
                   DESCRIPTION                           "Value of configuration register."
                   ::= { chassis 9 }

               configRegNext OBJECT-TYPE
                   SYNTAX  INTEGER
                   ACCESS  read-only
                   STATUS  deprecated
                   DESCRIPTION                           "Value of configuration register at next
                           reload."
                   ::= { chassis 10 }

               cardTable OBJECT-TYPE
                   SYNTAX  SEQUENCE OF CardTableEntry
                   ACCESS  not-accessible
                   STATUS  deprecated
                   DESCRIPTION                            "Chassis card table."
                   ::= { chassis 11 }

               cardTableEntry OBJECT-TYPE
                   SYNTAX CardTableEntry
                   ACCESS  not-accessible
                   STATUS  deprecated
                   DESCRIPTION                            "Chassis card table."
                   INDEX { cardIndex }
               ::= { cardTable 1 }

               CardTableEntry ::=
                   SEQUENCE {
                       cardIndex
                           INTEGER,
                       cardType
                           INTEGER,
                       cardDescr
                           DisplayString,
                       cardSerial
                           INTEGER,
                       cardHwVersion
                           DisplayString,
                       cardSwVersion
                           DisplayString,
                       cardSlotNumber
                           INTEGER,
                       cardContainedByIndex
                           INTEGER,
                       cardOperStatus
                           INTEGER,
                       cardSlots
                           INTEGER
                   }


          -- The following section describes the components of the
          -- table.

               cardIndex OBJECT-TYPE
                   SYNTAX  INTEGER
                   ACCESS  read-only
                   STATUS  deprecated
                   DESCRIPTION                           "Index into cardTable (not physical chassis
                           slot number)."
                   ::= { cardTableEntry 1 }


-- The expansions for some acronyms used for cardType enumerations are:
--	CSU : Channel Service Unit
--	DSU : Dial Service Unit
--	FT1 : Fractional T1
--	WIC : Wan Interface Card
--	DTR : Dedicated Token Ring
--	PM  : Port Module
--	PA  : Port Adapter

               cardType OBJECT-TYPE
                   SYNTAX  INTEGER {
			unknown(1)
			,csc1(2)
			,csc2(3)
			,csc3(4)
			,csc4(5)
			,rp(6)
			,cpu-igs(7)
			,cpu-2500(8)
			,cpu-3000(9)
			,cpu-3100(10)
			,cpu-accessPro(11)
			,cpu-4000(12)
			,cpu-4000m(13)
			,cpu-4500(14)
			,rsp1(15)
			,rsp2(16)
			,cpu-4500m(17)
			,cpu-1003(18)
			,cpu-4700(19)
			,csc-m(20)
			,csc-mt(21)
			,csc-mc(22)
			,csc-mcplus(23)
			,csc-envm(24)
			,chassisInterface(25)
			,cpu-4700S(26)
			,cpu-7200-npe100(27)
			,rsp7000(28)
			,chassisInterface7000(29)
			,rsp4(30)
			,cpu-3600(31)
			,cpu-as5200(32)
			,c7200-io1fe(33)
			,cpu-4700m(34)
			,cpu-1600(35)
			,c7200-io(36)
			,cpu-1503(37)
			,cpu-1502(38)
			,cpu-as5300(39)
			,csc-16(40)
			,csc-p(41)
			,csc-a(50)
			,csc-e1(51)
			,csc-e2(52)
			,csc-y(53)
			,csc-s(54)
			,csc-t(55)
			,csc-r(80)
			,csc-r16(81)
			,csc-r16m(82)
			,csc-1r(83)
			,csc-2r(84)
			,sci4s(56)
			,sci2s2t(57)
			,sci4t(58)
			,mci1t(59)
			,mci2t(60)
			,mci1s(61)
			,mci1s1t(62)
			,mci2s(63)
			,mci1e(64)
			,mci1e1t(65)
			,mci1e2t(66)
			,mci1e1s(67)
			,mci1e1s1t(68)
			,mci1e2s(69)
			,mci2e(70)
			,mci2e1t(71)
			,mci2e2t(72)
			,mci2e1s(73)
			,mci2e1s1t(74)
			,mci2e2s(75)
			,csc-cctl1(100)
			,csc-cctl2(101)
			,csc-mec2(110)
			,csc-mec4(111)
			,csc-mec6(112)
			,csc-fci(113)
			,csc-fcit(114)
			,csc-hsci(115)
			,csc-ctr(116)
			,cpu-7200-npe150(121)
			,cpu-7200-npe200(122)
			,cpu-wsx5302(123)
			,gsr-rp(124)
			,cpu-3810(126)
			,cpu-2600(127)
			,cpu-rpm(128)
			,cpu-ubr904(129)		-- CPU card for Cisco Cable Modem (ubr - universal broadband router)
			,cpu-6200-mpc(130)		-- Maintenance processor card for c6200
			,cpu-1700(131)			-- CPU for Cisco 1700 series
			,cpu-7200-npe300(132)		-- Network processing engine (CPU card) for 7200 series 
			,cpu-1400(133)			-- CPU for Cisco 1400 series 
			,cpu-800(134)			-- CPU for Cisco 800 series products 
			,cpu-psm-1gbps(135)		-- Processor Switch Module 1 with 1.2Gbps switching capacity for MGX 8800 series chassis
			,cpu-7200-npe175(137)		-- Network processing engine (CPU card) for 7200 series
			,cpu-7200-npe225(138)		-- Network processing engine (CPU card) for 7200 series
			,cpu-1417(140)			-- CPU for Cisco 1417 only
			,cpu-psm1-1oc12(141)		-- Cisco MGX8800 Processor Switch Module 1 with 1 622Mbps port
			,cpu-optical-regenerator(142)	-- CPU for the Cisco Optical Regenerator chassis
			,cpu-ubr924(143)		-- CPU for the UBR924 Cisco Cable Modem
			,cpu-7120(144)			-- CPU for the Cisco 7120 series
			,cpu-7140(145)			-- CPU for the Cisco 7140 series
			,cpu-psm1-2t3e3(146)		-- Cisco MGX8800 Processor Switch Module 1 with 2 T3/E3 ports
			,cpu-psm1-4oc3(147)		-- Cisco MGX8800 Processor Switch Module 1 with 4 155Mbps ports
			,cpu-ubr91x(149)		-- CPU card for the UBR91X family of Cable Modems (912-c, 912-s, 914)
			,sp(150)
			,eip(151)
			,fip(152)
			,hip(153)
			,sip(154)
			,trip(155)
			,fsip(156)
			,aip(157)
			,mip(158)
			,ssp(159)
			,cip(160)
			,srs-fip(161)
			,srs-trip(162)
			,feip(163)
			,vip(164)
			,vip2(165)
			,ssip(166)
			,smip(167)
			,posip(168)
			,feip-tx(169)
			,feip-fx(170)
			,cbrt1(178)
			,cbr120e1(179)
			,cbr75e(180)
			,vip2-50(181)
			,feip2(182)
			,acip(183)
			,mc11(184)			-- cable card 1 downstream 1 upstream
			,mc12a(185)			-- cable card 1 downstream 2 upstream 
			,io1fe-tx-isl(186)		-- Fast Ethernet I/O Controller which provides RJ45 and MII Connectors
			,geip(187)			-- Gigabit Ethernet Interface Processor 
			,vip4(188)			-- 4th Generation Versatile Interface Processor for the c7500 router 
			,mc14a(189)			-- cable card 1 downstream 4 upstream 
			,mc16a(190)			-- cable card 1 downstream 6 upstream 
			,mc11a(191)			-- modem card 1 downstream 1 upstream (ASIC)  
			,cip2(192)			-- channel interface processor 2 for the 7500 router family.  supports IBM ESCON and IBM Parallel (Bus & Tag) interface types.
			,mc28(194)			-- cable card 2 downstream 8 upstream
			,vip4-80(195)		-- 4th Generation Versatile Interface Processor for the c7500 router
			,vip4-50(196)		-- 4th Generation Versatile Interface Processor for the c7500 router, lower performance than vip4-80 card
			,io-e-ge(197)		-- C7200 I/O Controller with GE(1000Mbps) + E(10Mbps) interface
			,io-2fe(198)		-- C7200 I/O Controller with 2FE (10/100Mbps) interface
			,npm-4000-fddi-sas(200)
			,npm-4000-fddi-das(201)
			,npm-4000-1e(202)
			,npm-4000-1r(203)
			,npm-4000-2s(204)
			,npm-4000-2e1(205)
			,npm-4000-2e(206)
			,npm-4000-2r1(207)
			,npm-4000-2r(208)
			,npm-4000-4t(209)
			,npm-4000-4b(210)
			,npm-4000-8b(211)
			,npm-4000-ct1(212)
			,npm-4000-ce1(213)
			,npm-4000-1a(214)
     	                ,npm-4000-6e-pci(215)
			,npm-4000-1fe(217)
			,npm-4000-1hssi(218)
			,npm-4000-2e-pci(219)
			,npm-4000-4gb(220)			-- 4-Port Serial E1/G.703 

			,pa-1fe(230)
			,pa-8e(231)
			,pa-4e(232)
			,pa-5e(233)
			,pa-4t(234)
			,pa-4r(235)
			,pa-fddi(236)
			,sa-encryption(237)
			,pa-ah1t(238)
			,pa-ah2t(239)
			,pa-a4t(240)			
			,pa-a8t-v35(241)
			,pa-1fe-tx-isl(242)
			,pa-1fe-fx-isl(243)
			,pa-1fe-tx-nisl(244)
			,sa-compression(245)
			,pa-atm-lite-1(246)
			,pa-ct3(247)
			,pa-oc3sm-mux-cbrt1(248)
			,pa-oc3sm-mux-cbr120e1(249)
			,pa-ds3-mux-cbrt1(254)
			,pa-e3-mux-cbr120e1(255)
			,pa-8b-st(257)
			,pa-4b-u(258)
			,pa-fddi-fd(259)
			,pm-cpm-1e2w(260)
			,pm-cpm-2e2w(261)
			,pm-cpm-1e1r2w(262)
			,pm-ct1-csu(263)
			,pm-2ct1-csu(264)
			,pm-ct1-dsx1(265)
			,pm-2ct1-dsx1(266)
			,pm-ce1-balanced(267)
			,pm-2ce1-balanced(268)
			,pm-ce1-unbalanced(269)
			,pm-2ce1-unbalanced(270)
			,pm-4b-u(271)
			,pm-4b-st(272)
			,pm-8b-u(273)
			,pm-8b-st(274)
			,pm-4as(275)
			,pm-8as(276)
			,pm-4e(277)
			,pm-1e(278)
			,pm-m4t(280)
			,pm-16a(281)
			,pm-32a(282)
			,pm-c3600-1fe-tx(283)
			,pm-c3600-compression(284)
			,pm-dmodem(285)
			,pm-8admodem(286)
			,pm-16admodem(287)
			,pm-c3600-1fe-fx(288)
			,pm-1fe-2t1-csu(289)		-- Port Module with 1 Fast Ethernet, 2 T1 with CSU
			,as5200-carrier(290)
			,as5200-2ct1(291)
			,as5200-2ce1(292)
			,as5200-dtd-carrier(293)
			,pm-as5xxx-12m(310)
			,pm-as5xxx-12m-56k(311)
			,pm-as5xxx-12m-v110(312)
-- The expansions for some acronyms used in this section are given below:
--	CSU - Channel Service Unit
--	DSU - Dial Service Unit
--	FT1 - Fractional T1
--	WIC - Wan Interface Card
			,wm-c2500-5in1(330)
			,wm-c2500-t1-csudsu(331)
			,wm-c2500-sw56-2wire-csudsu(332)
			,wm-c2500-sw56-4wire-csudsu(333)
			,wm-c2500-bri(334)
			,wm-c2500-bri-nt1(335)
			,wic-serial-1t(360)
			,wic-serial-2t(361)
			,wic-csu-dsu-4(363)
			,wic-s-t-3420(364)
			,wic-s-t-2186(365)
			,wic-u-3420(366)
			,wic-u-2091(367)
			,wic-u-2091-2081(368)
			,wic-s-t-2186-leased(369)
			,wic-t1-csudsu(370)		-- FT1 CSU/DSU Wan Interface Card 
			,wic-serial-2as(371)		-- WAN Interface Card - 2 port Async/Sync
			,aim-compression(372)		-- Compression Advanced Interface Module (AIM)
			,c3660-2fe-tx(373)		-- c3660 onboard 2FE(TX) version
			,pm-oc3mm(374)			-- ATM OC3 multimode Port Module
			,pm-oc3mm-vpd(375)		-- ATM OC3 multimode Port Module with Voice Processing Deck
			,pm-oc3smi-vpd(376)		-- ATM OC3 single mode intermediate reach Port Module with Voice Processing Deck
			,pm-oc3sml-vpd(377)		-- ATM OC3 single mode long reach Port Module with Voice Processing Deck
			,pm-oc3sml(378)			-- ATM OC3 single mode long reach Port Module
			,pm-oc3smi(379)			-- ATM OC3 single mode intermediate reach Port Module
			,pm-ima-4t1(380)		-- 4 port T1 IMA (Inverse Mux for ATM) port module
			,pm-ima-8t1(381)		-- 8 port T1 IMA (Inverse Mux for ATM) port module 
			,pm-ima-4e1(382)		-- 4 port E1 IMA (Inverse Mux for ATM) port module 
			,pm-ima-8e1(383)		-- 8 port E1 IMA (Inverse Mux for ATM) port module
			,nm-1fe-2w(384)			-- Network Module with 1 Fast Ethernet and 2 WIC/VIC interfaces
			,nm-2fe-2w(385)			-- Network Module with 2 Fast Ethernet and 2 WIC/VIC interfaces
			,nm-1fe-1r-2w(386)		-- Network Module with 1 Fast Ethernet, 1 token ring, and 2 WIC/VIC interfaces
			,nm-2w(387)			-- Network Module with 2 WIC/VIC interfaces
			,c36xx-1fe-tx(389)		-- Onboard 1FE Interface for the c3660 chassis
			,pa-jt2(400)
			,pa-posdw(401)
			,pa-4me1-bal(402)
			,pa-2ce1-balanced(403)
			,pa-2ct1(404)
			,pa-1vg(405)
			,pa-atmdx-ds3(406)
			,pa-atmdx-e3(407)
			,pa-atmdx-sml-oc3(408)
			,pa-atmdx-smi-oc3(409)
			,pa-atmdx-mm-oc3(410)
			,pa-a8t-x21(414)
			,pa-a8t-rs232(415)
			,pa-4me1-unbal(416)
			,pa-4r-fdx(417)
			,pa-1e3(418)
			,pa-2e3(419)
			,pa-1t3(420)
			,pa-2t3(421)
			,pa-2ce1-unbalanced(422)
			,pa-14e-switch(423)
			,pa-1fe-fx-nisl(424)
			,pa-esc-channel(425)
			,pa-par-channel(426)
			,pa-ge(427)			-- Gigabit Ethernet Port Adapter
			,pa-4ct1-csu(428)		-- 8 Port Channelized T1 with CSU 
			,pa-8ct1-csu(429)		-- 8 Port Channelized T1 with CSU
			,c3800-vdm(430)
			,c3800-vdm-dc-2t1e1(431)
			,c3800-vdm-dc-1t1e1-enet(432)
			,pa-2feisl-tx(433)
			,pa-2feisl-fx(434)
			,mc3810-dcm(435)
			,mc3810-mfm-e1balanced-bri(436)
			,mc3810-mfm-e1unbalanced-bri(437)
			,mc3810-mfm-e1-unbalanced(438)
			,mc3810-mfm-dsx1-bri(439)
			,mc3810-mfm-dsx1-csu(440)
			,mc3810-vcm(441)	
			,mc3810-avm(442)
			,mc3810-avm-fxs(443)
			,mc3810-avm-fxo(444)
			,mc3810-avm-em(445)
			,mc3810-vcm3(446)		-- MC3810 Voice Compression Module with 3 DSPs (Digital Signal Processor) 
			,mc3810-bvm(447)		-- MC3810 Basic Voice Module
			,mc3810-avm-fxo-uk(448)		-- MC3810 Analog Voice Module UK Foreign eXchange Office
			,mc3810-avm-fxo-ger(449)	-- MC3810 Analog Voice Module Germany Foreign eXchange Office
			,mc3810-hcm2(450)		-- MC3810 High (Voice) Compression Module with 2 DSPs (Digital Signal Processor)
			,mc3810-hcm6(451)		-- MC3810 High (Voice) Compression Module with 6 DSPs (Digital Signal Processor) 
			,mc3810-avm-fxo-pr3(452)	-- MC3810 Analog Voice Module Singapore or Japan Foreign eXchange Office
			,mc3810-avm-fxo-pr2(453)	-- MC3810 Analog Voice Module Australia or New Zealand Foreign eXchange Office
			,mc3810-vdm(454)		-- MC3810 Video Dial-up Module
			,mc3810-apm-fxs-did(455)	-- MC3810 Foreign Exchange Station (FXS) Direct Inward Dialing (DID) Analog Personality Module
			,mc3810-bvm-nt-te(456)		-- 4 ports NT or TE BRI Voice Module on MC3810
			,mc3810-hcm1(457)		-- High performance compression module for the MC3810 platform equipped with one TI 549 DSP
			,mc3810-hcm3(458)		-- High performance compression module for the MC3810 platform equipped with three TI 549 DSPs
			,mc3810-hcm4(459)		-- High performance compression module for the MC3810 platform equipped with four TI 549 DSPs
-- 460 available
			,pm-dtd-6m(461)
			,pm-dtd-12m(462)		-- mica 12 modem module 
			,as5300-4ct1(480)
			,as5300-4ce1(481)
			,as5300-carrier(482)
			,as5300-dtd-carrier(484)
			,as5300-8ct1-4t(485)		-- Channelized octal T1 and 4 serial card
			,as5300-8ce1-4t(486)		-- Channelized octal E1 and 4 serial card
			,as5300-4ct1-4t(487)		-- Channelized quad T1 and 4 serial card
			,as5300-4ce1-4t(488)		-- Channelized quad E1 and 4 serial card
			,as5300-amazon2-carrier(489)	-- Amazon II mica carrier card
			,vic-em(500)
			,vic-fxo(501)
			,vic-fxs(502)
			,vpm-2v(503)
			,vpm-4v(504)
			,dsp-vfc30(505)
			,dspm-c542(507)			-- DSP (Digital Signal Processor) C542  module for the AS5300 and AS5800 series
			,vic-2fxo-eu(508)		-- 2 port Foreign eXchange Office Voice Interface Cards for most of Europe 
			,vic-2fxo-m3(509)		-- 2 port Foreign eXchange Office Voice Interface Cards for Australia 
			,vic-2fxo-m4(510)		-- 2 port Foreign eXchange Office Voice Interface Cards for Germany
			,vic-2fxo-m5(511)		-- 2 port Foreign eXchange Office Voice Interface Cards for France
			,vic-2fxo-m6(512)		-- 2 port Foreign eXchange Office Voice Interface Cards for Italy
			,vic-2fxo-m7(513)		-- 2 port Foreign eXchange Office Voice Interface Cards for Portugal
			,vic-2fxo-m8(514)		-- 2 port Foreign eXchange Office Voice Interface Cards for Singapore 
			,vic-2st-2086(515)		-- 2 port Terminal Endpoint BRI S/T Voice interface daughter card
			,hdv(516)                       -- High Density Voice over IP network module
			,dspm-6c549(517)		-- DSP (Digital Signal Processor) module that contains 6 C549 DSPs, used in AS5300 and AS5800
			,wvic-1dsu-t1(518)-- WAN Voice Interface Card with a single port T1 DSU for 1600, 1700, 2600, or 3600 series 
			,wvic-1dsu-e1(519)		-- WAN Voice Interface Card with a single port E1 DSU for 1600, 1700, 2600, or 3600 series 
			,wvic-2dsu-t1(520)		-- WAN Voice Interface Card with a dual port T1 DSU for 1600, 1700, 2600, or 3600 series
			,wvic-2dsu-e1(521)		-- WAN Voice Interface Card with a dual port E1 DSU for 1600, 1700, 2600, or 3600 series
			,wvic-2dsu-t1-di(522)		-- WAN Voice Interface Card with a dual port T1 DSU with Drop and Insert for 1600, 1700, 2600, or 3600 series
			,wvic-2dsu-e1-di(523)           -- WAN Voice Interface Card with a dual port E1 DSU with Drop and Insert for 1600, 1700, 2600, or 3600 series 
			,vic-2fxo-m2(525)		-- 2 port Foreign eXchange Office Voice Interface Cards (Module 2) for Europe/Australia/New Zealand
			,hda-nm-4fxs(528)		-- High Density Analog Voice Module 

			,pos-qoc3-mm(530)
			,pos-qoc3-sm(531)
			,pos-oc12-mm(532)
			,pos-oc12-sm(533)
			,atm-oc12-mm(534)
			,atm-oc12-sm(535)
			,pos-oc48-mm-l(536)
			,pos-oc48-sm-lr-fc(537)		-- GSR 1 port Packet Over Sonet OC-48, single mode, long reach, FC connector card
			,gsr-sfc(538)
			,gsr-csc(539)
			,gsr-csc4(540)
			,gsr-csc8(541)
			,gsr-sfc8(542)
			,atm-qoc3-sm(543)               -- Quad OC3 Line Card ATM Singlemode Fiber Ports
			,atm-qoc3-mm(544)               -- Quad OC3 Line Card ATM Multimode Fiber Ports
			,gsr-oc12chds3-mm(545)		-- OC12 channelised to DS3 multimode
			,gsr-oc12chds3-sm(546)		-- OC12 channelised to DS3 singlemode
			,gsr-1ge(547)			-- GSR 1 Port Gigabit Ethernet Line Card 
			,gsr-oc12chsts3-mm(548)		-- GSR OC12 channelized to STS-3c/STM-1 multi-mode line card
			,gsr-oc12chsts3-sm(549)		-- GSR OC12 channelized to STS-3c/STM-1 single-mode line card
			,pos-oc48-sm-sr-fc(552)		-- GSR 1 Port Packet Over SONET OC-48c/STM-16 Single Mode Short Reach with FC connector
			,pos-qoc3-sm-l(553)		-- GSR 4 Port Packet Over SONET OC-3c/STM-1 Single Mode Long Reach
			,pos-8oc3-mm(554)		-- GSR 8 port OC3 Multimode POS 
			,pos-8oc3-ir(555)		-- GSR 8 port OC3 SM intermediate reach POS 
			,pos-8oc3-lr(556)		-- GSR 8 port OC3 SM long reach POS 
			,pos-16oc3-mm(557)		-- GSR 16 port OC3 multimode POS 
			,pos-16oc3-ir(558)		-- GSR 16 port OC3 SM intermediate reach POS 
			,pos-16oc3-lr(559)		-- GSR 16 port OC3 SM long reach POS
			,pa-8ct1(560)			-- 8 Port Channelized T1
			,pa-8ce1(561)			-- 8 Port Channelized E1
			,pa-ce3(562)			-- Channelized E3 Port Adapter
			,pa-4r-dtr(563)			-- 4 port Dedicated Token Ring port adapter 
			,pa-possw-sm(564)		-- Single Width POS (Packet Over Sonet) Port Adapter with Singlemode Fiber
			,pa-possw-mm(565)		-- Single Width POS (Packet Over Sonet) Port Adapter with Multimode Fiber
			,pa-possw-lr(566)		-- Single Width POS (Packet Over Sonet) Port Adapter with Long Range Fiber
			,pa-1t3-plus(567)		-- Improved one port serial T3 plus port adapter
			,pa-2t3-plus(568)		-- Improved 2 port serial T3 plus port adapter
			,pa-ima-t1(569)			-- Implements IMA functionality for the 7200/7500 platform for a T1
			,pa-ima-e1(570)			-- Implements IMA functionality for the 7200/7500 platform for an E1
			,pa-2ct1-csu(571)		-- 2 port multichannel T1 port adapter with built in csu/dsu for the 7200, 7500, and rsp7000 platforms
			,pa-2ce1(572)			-- 2 port multichannel E1 port adapter for the 7200, 7500, and rsp7000 platforms 
			,pa-2fe-tx(573)			-- 2-port FastEthernet port adapter with two RJ-45 interfaces 
			,pa1-esc4-channel(575)		-- High Performance ESCON Channel Port Adapter Version 4 
			,pa2-oc3-pos-sw(576)		-- Dual Port OC-3c Packet Over Sonet(POS) Single Wide Adapter Card
			,pa-4dtr(577)			-- Four port dedicated tokenring adapter
			,pa-vm-hda-8fxs-did(578)	-- High density analog voice/fax voice module with 8 FXS/DID
			,pa1-oc3-pos-sw(579)		-- Single port OC-3c Packet over Sonet (POS) Single Wide Port Adapter Card

			,pm-1fe-1t1(600)		-- Port Module with 1 Fast Ethernet, 1 T1
			,pm-1fe-2t1(601)		-- Port Module with 1 Fast Ethernet, 2 T1
			,pm-1fe-1e1(602)		-- Port Module with 1 Fast Ethernet, 1 E1
			,pm-1fe-2e1(603)		-- Port Module with 1 Fast Ethernet, 2 E1
			,pm-1fe-1t1-csu(604)            -- Port Module with 1 Fast Ethernet, 1 T1 with CSU 
			,pm-atm25(605)			-- 25 Mbits/sec ATM Port Module
			,pm-hssi(606)			-- HSSI Card Port Module 
			,as5800-dsc(630)
			,as5800-12t1(631)
			,as5800-12e1(632)
			,as5800-mica-hmm(633)
			,as5800-t3(634)			-- T3 trunk card
			,as5800-1fe-dsi(635)
			,as5800-mica-dmm(636)		-- Mica Double density Modem Module
			,as5800-vcc(637)		-- Voice Carrier Card for the AS5800
			,as5800-dspm-6c549(638)		-- Digital Signal Processor Module with 6 C549's Voice Feature Card for the AS5800
			,as5800-dsp(639)		-- Digital Signal Processor Voice Feature Card for the AS5800
--	650-699:	c6xxx cards
			,slc-cap8(650)			-- Subscriber line card for c6200 - Carrierless Amplitude and Phase modulation - 8 port variation 
			,ntc-oc3si(651)			-- Network Trunk card for c6200 - Optical Carrier 3, single-mode, intermediate reach variation
			,ntc-oc3mm(652)			-- Network Trunk card for c6200 -  Optical Carrier 3, multi-mode reach variation
			,ntc-stm1si(653)		-- Network Trunk card for c6200 - Synchronous Transport Module level 1, single-mode, intermediate reach variation 
			,ntc-stm1mm(654)		-- Network Trunk card for c6200 - Synchronous Transport Module level 1, multi-mode variation
			,slc-dmt8(655)			-- Subscriber line card for c6200 - Discrete Multi-Tone 8 port variation
			,slc-dmt16(656)			-- Subscriber line card for c6200 - Discrete Multi-Tone 16 port variation
			,ntc-ds3(657)			-- Network Trunk card for c6200 - DS3
			,osm-1oc48-pos-ss(659)		-- Optical Service Module, 1-Port OC48 POS SS w/ 4 GE
			,osm-1oc48-pos-sl(660)		-- Optical Service Module, 1-Port OC48 POS SL w/ 4 GE
			,osm-1oc48-pos-si(661)		-- Optical Service Module, 1-Port OC48 POS SI w/ 4 GE
			,osm-2oc12-pos-sl(664)		-- Optical Service Module, 2-Port OC12 POS SL w/ 4 GE
			,osm-4oc12-pos-sl(665)		-- Optical Service Module, 4-Port OC12 POS SL w/ 4 GE
			,osm-2oc12-pos-mm(666)		-- Optical Service Module, 2-Port OC12 POS MM w/ 4 GE
			,osm-4oc12-pos-mm(667)		-- Optical Service Module, 4-Port OC12 POS MM w/ 4 GE
			,osm-2oc12-pos-si(668)		-- Optical Service Module, 2-Port OC12 POS SI w/ 4 GE
			,osm-4oc12-pos-si(669)		-- Optical Service Module, 4-Port OC12 POS SI w/ 4 GE
			,osm-8oc3-pos-si(670)		-- Optical Service Module, 8-Port OC3 POS SI w/ 4 GE
			,osm-16oc3-pos-si(671)		-- Optical Service Module, 16-Port OC3 POS SI w/ 4 GE
			,osm-8oc3-pos-mm(672)		-- Optical Service Module, 8-Port OC3 POS MM w/ 4 GE
			,osm-16oc3-pos-mm(673)		-- Optical Service Module, 16-Port OC3 POS MM w/ 4 GE
			,osm-8oc3-pos-sl(674)		-- Optical Service Module, 8-Port OC3 POS SL w/ 4 GE
			,osm-16oc3-pos-sl(675)		-- Optical Service Module, 16-Port OC3 POS SL w/ 4 GE
			,osm-4ge-wan-gbic(676)		-- Optical Service Module, 4-Port GE w/ WAN services
			,osm-4ge-4oc12-chds3-sm-ir(680)	-- Optical Service Module, 4-Port OC12 channelized down to DS3 Singlemode Intermediate range with 4 GE
			,osm-4ge-8oc12-chds3-sm-ir(681) -- Optical Service Module, 8-Port OC12 channelized down to DS3 Singlemode Intermediate range with 4 GE
			,osm-4ge-oc48-chds3-sm-sr(682)	-- Optical Service Module, 1-Port OC48 channelized down to DS3 Singlemode Short range with 4 GE
			,osm-4ge-2oc48-chds3-sm-sr(683)	-- Optical Service Module, 2-Port 0C48 channelized down to DS3 Singlemode Short range with 4 GE
			,osm-4ge-oc48-chds3-sm-ir(684)	-- Optical Service Module, 1-Port OC48 channelized down to DS3 Singlemode Intermediate range with 4 GE
			,osm-4ge-2oc48-chds3-sm-ir(685)	-- Optical Service Module, 2-Port OC48 channelized down to DS3 Singlemode Intermediate range with 4 GE
			,osm-4ge-oc12-chds3-sm-ir(686)	-- Optical Service Module, 1-Port OC12 channelized down to DS3 Single Mode Intermediate range with 4 GE
			,osm-4ge-2oc12-chds3-sm-ir(687)	-- Optical Service Module, 2-Port OC12 channelized down to DS3 Single Mode Intermediate range with 4 GE
			,wsx-6582-2pa(689)		-- Flex-Wan2 line card for Catalyst 6xxx - 2-WAN PA line card ws-x6582-2pa
			,wsx-6066-slbsk9(692)		-- CSM-S is a content switching module with integrated SSL acceleration
			,cat6k-wsf-6k-pfc3b(693)		-- Catalyst 6500 Policy feature card 3B
			,cat6k-wsf-6k-dfc3b(694)		-- Catalyst 6500 Distributed forwarding card 3B
			,cat6k-wsf-6700-dfc3b(695)		-- Catalyst 6500 Distributed forwarding card 3B
			,cat6k-wsf-6k-pfc3bxl(696)		-- Catalyst 6500 Policy feature card 3B XL
			,cat6k-wsf-6k-dfc3bxl(697)		-- Catalyst 6500 Distributed forwarding card 3B XL
			,cat6k-wsf-6700-dfc3bxl(698)		-- Catalyst 6500 Distributed forwarding card 3B XL

			,atmdx-rpm(750)			-- RPM Cell Bus Interface
			,pa-atm-oc12-mm(802)		-- Multimode ATM OC-12 Port Adapter 
			,pa-atm-oc12-smi(803)		-- Singlemode ATM OC-12 Intermediate reach Port Adapter 
			,pa-mct3(804)			-- Multichannel DS3 single port adapter
			,pa-mc2t3(805)			-- Multichannel DS3 dual port adapter
			,pa-pos-oc12-mm(806)		-- OC-12 Packet Over SONET Port Adapter, Multi-Mode fiber
			,pa-pos-oc12-sm(807)		-- OC-12 Packet Over SONET Port Adapter, Single Mode fiber
			,srp-pa-oc12-mm(808)		-- SRP OC-12/STM-4 Multimode Port Adapter for 7000 series
			,srp-pa-oc12-sm-ir(809)		-- SRP OC-12/STM-4 Single Mode Intermediate Reach Port Adapter for 7000 series
			,srp-pa-oc12-lr(810)		-- SRP OC-12/STM-4 Single Mode Long Reach Port Adapter for 7000 series
			,pa-mcx-2te1(811)		-- 2 port, software configurable Multichannel T1/E1 with TDM Port Adapter
			,pa-mcx-4te1(812)		-- 4 port, software configurable Multichannel T1/E1 with TDM Port Adapter
			,pa-mcx-8te1(813)		-- 8 port, software configurable Multichannel T1/E1 with TDM Port Adapter
			,srp-pa-oc12-sm-xr(814)	-- SRP OC-12/STM-4 Single Mode Extended Reach Port Adapter for 7000 series
			,pa-mc-stm1-smi(817)		-- channelized STM-1 PA for 7500/7200(single mode intermediate reach)
			,pa-dual-wide-ge(819)		-- Dual Wide Enhanced Gigabit Ethernet Port Adapter
			,pa-vxa-1t1e1-24(820)		-- 1 port T1/E1 voice port adapter w/ 7 DSPs
			,pa-vxa-1t1e1-30(821)		-- 1 port T1/E1 voice port adapter w/ 8 DSPs
			,pa-mc-8t1e1(822)		-- Multichannel T1/E1 (without TDM) Port Adapter
			,pa-mcx-8te1-m(824)		-- 8 port, software configurable Multichannel T1/E1 SS7 with TDM Port Adapter
			,pa-a6-mm-oc3(825)              -- ATM WAN OC3 MM Port Adapter.
			,pa-a6-smi-oc3(826)             -- ATM WAN OC3 SMI Port Adapter.
			,pa-a6-sml-oc3(827)             -- ATM WAN OC3 SML Port Adapter.
			,pa-a6-ds3(828)                 -- ATM WAN OC3 DS3 Port Adapter.
			,pa-a6-e3(829)                  -- ATM WAN OC3 E3 Port Adapter.

			,ausm-8t1(850)			-- ATM User Network Interface Service Module with 8 T1 ports
			,ausm-8e1(851)			-- ATM User Network Interface Service Module with 8 E1 ports
			,cesm-8t1(852)			-- Circuit Emulation Service Module with 8 T1 ports
			,cesm-8e1(853)			-- Circuit Emulation Service Module with 8 E1 ports
			,frsm-8t1(854)			-- Frame Relay Service Module with 8 T1 ports
			,frsm-8e1(855)			-- Frame Relay Service Module with 8 E1 ports
			,frsm-4x21(856)			-- Frame Relay Service Module supporting 4 high speed X.21 ports
			,frsm-2hssi(857)		-- Frame Relay Service Module supporting 2 high speed HSSI ports
			,cesm-1t3(858)			-- Circuit Emulation Service Module (CESM) with one T3 port
			,cesm-1e3(859)			-- Circuit Emulation Service Module (CESM) with one E3 port
			,vism-8t1(860)			-- Voice Interworking Service Module (VISM) with 8 T1 ports
			,vism-8e1(861)			-- Voice Interworking Service Module (VISM) with 8 E1 ports
			,mgx-rpm(862)			-- MGX8800 Route Processor Module having the functionality of a C7200 router
			,mgx-srm-3t3(863)		-- MGX8800 Service Redundancy Module supporting 3 T3 ports on back card, used for providing 1:N redundancy for T1 modules
			,vism-pr-8t1(899)	-- Voice Interworking Service Module Premium Card (VISM-PR)with 8 T1 ports
			,wsx-2914(900)			-- 4 port 10/100BaseTX module for Catalyst 2900XL series
			,wsx-2922(901)			-- 2 port 100BaseFX module for Catalyst 2900XL series
			,wsx-2914-v(902)		-- 4 port 10/100BaseTX ISL module for Catalyst 2900XL series
			,wsx-2922-v(903)		-- 2 port 100BaseFX ISL module for Catalyst 2900XL series
			,wsx-2924-v(904)		-- 4 port 100BaseFX module for Catalyst 2900XL series
			,wsx-2951(905)			-- ATM UTP module for Catalyst 2900XL series
			,wsx-2961(906)			-- ATM MMF module for Catalyst 2900XL series
			,wsx-2971(907)			-- ATM SMF-MR module for Catalyst 2900XL series
			,wsx-2972(908)			-- ATM SMF-LR module for Catalyst 2900XL series
			,wsx-2931(909)			-- GBIC Gigabit module for Catalyst 2900XL series
			,lm-bnc-2t3(950)		-- Two T3 75-ohm BNC back card
			,lm-bnc-2e3(951)		-- Two E3 75-ohm BNC back card
			,lm-db15-4x21(952)		-- Four X.21 DB-15 back card
			,lm-scsi2-2hssi(953)		-- Two HSSI SCSI-2 back card
			,lm-rj48-8t1(954)		-- Eight T1 RJ48 back card
			,lm-rj48-8t1-r(955)		-- Eight T1 RJ48 redundancy back card
			,lm-rj48-8e1(956)		-- Eight E1 RJ48 back card
			,lm-rj48-8e1-r(957)		-- Eight E1 RJ48 redundancy back card
			,lm-smb-8e1(958)		-- Eight E1 SMB back card
			,lm-smb-8e1-r(959)		-- Eight E1 SMB redundancy back card
			,lm-psm-ui(960)			-- User Interface back card containing 2 RS-232 ports and one ethernet port, T1/E1 timing reference ports for Processor Switch Modules
			,lm-mmf-4oc3(961)		-- 4 port 155Mbps back card, MMF, SC connectors
			,lm-smfir-4oc3(962)		-- 4 port 155Mbps back card, SMF-IR, SC connectors
			,lm-smflr-4oc3(963)		-- 4 port 155Mbps back card, SMF-LR, SC connectors
			,lm-smfir-1oc12(964)		-- 1 port 622Mbps back card, SMF-IR, FC connectors
			,lm-smflr-1oc12(965)		-- 1 port 622Mbps back card, SMF-LR, FC connectors
			,lm-s3-ui(966)			-- Processor Switch Module (PXM) Stratum 3 User Interface back card for PXM1 or PXM2
			,lm-1fe-tx(967)			-- 1 port Fast Ethernet RJ45 connector back card for MGX8800 RPM module
			,lm-1fe-fx(968)			-- 1 port Fast Ethernet MMF connector back card for MGX8800 RPM module
			,lm-1mmf-fddi(969)		-- 1 port FDDI MMF connector back card for MGX8800 RPM module
			,lm-1smf-fddi(970)		-- 1 port FDDI SMF connector back card for MGX8800 RPM module
			,lm-rj45-4e(971)		-- 4 port Ethernet (10BaseT) RJ45 connector back card for MGX8800 RPM module
			,lm-bnc-3t3(985)		--  3 T3  Back Card , BNC Connector
			,ubr-mc16s(1001)		-- Cable card 1 downstream 6 upstream for Spectrum management
			,ubr-mc11(1002)		-- Cable linecard 1 downstream, 1 upstream, FPGA
			,ubr-mc11c(1003)	-- Cable linecard 1 downstream, 1 upstream, ASIC C
			,ubr-mc12c(1004)	-- Cable linecard 1 downstream, 2 upstream, ASIC C
			,ubr-mc14c(1005)	-- Cable linecard 1 downstream, 4 upstream, ASIC C
			,ubr-mc16a(1006)	-- Cable linecard 1 downstream, 6 upstream, ASIC A
			,ubr-mc16b(1007)	-- Cable linecard 1 downstream, 6 upstream, ASIC B
			,ubr-mc16c(1008)	-- Cable linecard 1 downstream, 6 upstream, ASIC C
			,ubr-mc16e(1009)	-- Cable linecard 1 downstream, 6 upstream, ASIC for Europe
			,ubr-mc28c(1010)		-- Cable linecard 2 downstream, 8 upstream 
			,ubr-mc26(1011)		-- Cable linecard 2 downstream, 6 upstream
			,ubr-912c(1012)		-- Cisco uBR912-C Cable Modem Card with CSU/DSU WIC
			,ubr-912s(1013)		-- Cisco uBR912-S Cable Modem Card with Serial WIC
			,ubr-914r(1014)		-- Cisco uBR914 Cable Modem with removable WIC
			,ubr-clk(1015)		-- Cisco Cable Clock Card that provides the national clock signal to Cisco uBR7200 VXR
			,ubr-925(1016)		-- Cisco UBR925 Cable Modem/Router with VOIP and hardware accelerated IPSEC
			,ubr-mc26c(1017)	-- Cable linecard 2 downstream, 6 upstream
			,ubr-mc28cf(1020)	-- Cable linecard 2 downstream, 8 upstream, with F connector
			,ubr-mc28c-bnc(1021)	-- Cable linecard 2 downstream, 8 upstream, with BNC connector
			,ubr-mc26cf(1022)	-- Cable linecard 2 downstream, 6 upstream, with F connector
			,ubr-mc26c-bnc(1023)	-- Cable linecard 2 downstream, 6 upstream, with BNC connector
			,ubr-905(1024)		-- Cisco uBR905 Cable Modem with hardware accelerated IPSEC
			,ubr-dlc24(1025)	-- DLC24 is a Digital Video Broadcasting (DVB) Linecard which supports the DVB in-band (IB) and out-of-band (OOB) standards, as well as the DAVIC OOB standard. It has 2 downstream channels, 4 upstream channels, and 1 ASI interface port
			,ubr-mc520s-f(1029)	-- Cable linecard, 5 downstreams, 20 upstreams, with Spectrum Management, with F connector
			,ubr-mc520s-bnc(1030)	-- Cable linecard, 5 downstreams, 20 upstreams, with Spectrum Management, with BNC connector
			,ubr-tccplus(1040)	--  uBR10K Timing, Communications and Control Plus Card

			,gsr-8fe-tx(1050)		-- GSR 8 port Fast Ethernet card with Copper interface 
			,gsr-8fe-fx(1051)		-- GSR 8 port Fast Ethernet card with Fiber interface 
			,ssrp-oc48-sm-sr(1052)		-- GSR 1 port SONET based SRP OC-48c/STM-16 Single Mode, Short Reach 
			,ssrp-oc48-sm-lr(1053)		-- GSR 1 port SONET based SRP OC-48c/STM-16 Single Mode, Long Reach 
			,pos-qoc12-sm-lr(1054)		-- GSR 4 port (Quad) OC-12 POS card, single mode, long reach
			,pos-qoc12-mm-sr(1055)		-- GSR 4 port (Quad) OC-12 POS card, multi mode, short reach
			,pos-oc48-sm-lr-sc(1056)	-- GSR 1 port Packet Over Sonet OC-48, single mode, long reach, SC connector card
			,pos-oc48-sm-sr-sc(1057)	-- GSR 1 port Packet Over Sonet OC-48, single mode, short reach, SC connector card
			,srp-oc12-sm-ir(1058)		-- GSR 1 port single mode SRP OC-12/STM-4 intermediate reach module
			,srp-oc12-sm-lr(1059)		-- GSR 1 port single mode SRP OC-12/STM-4 long reach module
			,srp-oc12-mm(1060)		-- GSR 1 port SRP OC-12/STM-4 Multimode Ring line card
			,pos-en-oc48-sr-sc(1061)	-- GSR enhanced OC-48 short reach SC connector line card
			,pos-en-oc48-sr-fc(1062)	-- GSR enhanced OC-48 short reach FC connector line card
			,pos-en-oc48-lr-sc(1063)	-- GSR enhanced OC-48 long reach SC connector line card
			,pos-en-oc48-lr-fc(1064)	-- GSR enhanced OC-48 long reach FC connector line card
			,pos-en-qoc12-sr(1065)		-- GSR enhanced 4 port OC-12 short reach line card
			,pos-en-qoc12-ir(1066)		-- GSR enhanced 4 port OC-12 intermediate reach line card 
			,copper-6ds3(1067)		-- GSR 6 port copper DS3 interface line card
			,copper-12ds3(1068)		-- GSR 12 port copper DS3 interface line card
			,gsr-sfc16(1073)		-- GSR Switch Fabric Card for 12016
			,gsr-csc16(1074)		-- GSR 12016 Clock Scheduler Card
			,gsr-3ge(1075)			-- GSR 3 Port Gigabit Ethernet Line Card 
			,gsr-alarm16(1076)		-- GSR Alarm module
			,gsr-bus-board16(1077)		-- GSR Bus Board for Power distribution
			,srp-oc12-sm-xr(1078)		-- GSR 1 port single mode SRP OC-12/STM-4 extra long reach module	
			,pos-en-qoc12-mm(1079)		-- GSR enhanced 4 port OC-12 multimode line card 
			,pos-en-qoc48-sm-sr-fc(1080)	-- GSR enhanced 4 Port Packet Over Sonet OC-48, Single Mode, Short Reach, FC Connector Card
			,pos-en-qoc48-sm-sr-sc(1081)	-- GSR enhanced 4 Port Packet Over Sonet OC-48, Single Mode, Short Reach, SC Connector Card
			,pos-en-qoc48-sm-lr-sc(1082)	-- GSR enhanced 4 Port Packet Over Sonet OC-48, Single Mode, Long Reach, SC Connector Card
			,pos-en-qoc48-sm-lr-fc(1083)	-- GSR enhanced 4 Port Packet Over Sonet OC-48, Single Mode, Long Reach, FC Connector Card
			,gsr-6ct3(1084)			-- GSR 6 Port Channelized T3 Line Card 
			,pos-en-oc192-sm-lr-fc(1085)	-- GSR enhanced 1 Port Packet Over Sonet OC-192, Single Mode, Long Reach, FC Connector Card
			,pos-en-oc192-sm-lr-sc(1086)	-- GSR enhanced 1 Port Packet Over Sonet OC-192, Single Mode, Long Reach, SC Connector Card
			,pos-en-oc192-sm-vsr-sc(1087)	-- GSR enhanced 1 Port Packet Over Sonet OC-192, Single Mode, Very Short Reach, SC Connector Card
			,pos-en-oc192-sm-vsr-fc(1088)	-- GSR enhanced 1 Port Packet Over Sonet OC-192, Single Mode, Very Short Reach, FC Connector Card
			,gsr-sfc16-oc192(1091)		-- GSR 12016 OC192 Switch Fabric Card
			,gsr-csc16-oc192(1092)		-- GSR 12016 OC192 Clock Scheduler Card
			,gsr-qoc12-chstsds3-sm-ir-sc(1094)	-- GSR 4 port OC12 channelized to STS-12c/STM-4, STS-3c/STM1, or DS-3, Single Mode, Intermediate Reach and SC connector line card
			,gsr-qoc12-chstsds3-mm-sr-sc(1095)	-- GSR 4 port OC12 channelized to STS-12c/STM-4, STS-3c/STM1, or DS-3, Multi Mode, Short Reach and SC connector line card
			,gsr-oc48-chstsds3-mm-sr-sc(1096)	-- GSR 1 port OC48 channelized to STS-48c/STM16, STS-12c/STM-4, STS-3c/STM1 or DS-3, Multi Mode, Short Reach  and SC  connector line card 
			,gsr-oc48-chstsds3-sm-ir-sc(1097)	-- GSR 1 port OC48 channelized to STS-48c/STM16, STS-12c/STM-4, STS-3c/STM1 or DS-3, Single Mode, Intermediate Reach and SC connector line card
			,gsr-oc48-chstsds3-sm-lr-sc(1098)	-- GSR 1 port OC48 channelized to STS-48c/STM16, STS-12c/STM-4, STS-3c/STM1 or DS-3, Single Mode, Long Reach and SC connector line card
			,gsr-16oc3-chstsds3-mm-sr-sc(1099)	--  GSR 16 port OC3 channelized to STS-3c/STM-1 or DS-3; Multi Mode fiber, Short Reach, SC connector line card
			,aim-lc-4e1-compression(1100)	-- Lowcost 4 E-1 Compression AIM 
			,wic-csu-dsu-ft1(1105)		-- Wan Interface Card with 1 Fractional T1 DSU/CSU port for 2600, 3600 series
			,pm-ds3(1106)		-- ATM DS3 port module for 2600, 3600 series
			,pm-e3(1107)		-- ATM E3 port module for 2600, 3600 series
			,vic-2vp-fxs-did(1111)			-- 2 Port Voice Interface Card for 26/3600 Platforms.  Ports can function as Foreign Exchange Station (FXS)or Direct Inward Dialing (DID) Voice Ports (VP)
			,wic-serial-1t-12in1(1112)		-- WAN Interface Card card including 1 port serial interface, 12 in 1 connector type
			,vic-2st-2086-nt-te(1113)		-- Two port NT or TE Endpoint BRI S/T voice interface daughtercard
			,nm-aic64(1114)			-- The new alarm interface card (AIC) network module with 64 monitoring points on the C26xx/C3600 platform
			,mix3660-64(1115)		--  TDM Module that enables TDM switching on C3660 platform
			,wic-async-1am(1116)		--  WAN Interface Card - 1 Port Analog Modem
			,wic-async-2am(1117)		--  WAN Interface Card - Dual Analog Modem
			,hdv-4fxs(1120)			-- 4-Port FXS High Density Analog Voice Module
			,c2610m(1121)			-- c2600M with 1 integrated ethernet interface
			,c2611m(1122)			-- c2600M with 2 integrated ethernet interfaces
			,wic-ethernet(1124)		-- WIC-1ENET card for 17xx platforms
			,nm-1t3e3(1130)			-- One port Clear T3/E3 Network Module
			,nm-1ct3e3(1131)		-- One port Channelized T3/E3 Network Module
			,nm-8ct1e1(1132)		-- Eight port Channelized T1/E1 Network Module
			,hda-em-4fxo(1133)              -- 4-port FXO Expansion Module for High Density Analog Voice Interface Daughtercard
                        ,c2610xm-1fe(1134)                  -- Card with 1 integrated fast ethernet interface with SDRAM for Cisco 2610XM platform
                        ,c2611xm-2fe(1135)                  -- Card with 2 integrated fast ethernet interfaces with SDRAM for Cisco 2611XM platform
                        ,c2620xm-1fe(1136)                  -- Card with 1 integrated fast ethernet interface with SDRAM for Cisco 2620XM platform
                        ,c2621xm-2fe(1137)                  -- Card with 2 integrated fast ethernet interfaces with SDRAM for Cisco 2621XM platform
                        ,c2650xm-1fe(1138)                  -- Card with 1 integrated fast ethernet interface with SDRAM for Cisco 2650XM platform
                        ,c2651xm-2fe(1139)                  -- Card with 2 integrated fast ethernet interfaces with SDRAM for Cisco 2651XM platform
			,nm-1ct1e1-pri(1147)		-- One port Primary Rate Interface (PRI)  Channelized T1/E1 Network Module 
			,nm-2ct1e1-pri(1148)		-- Two port Primary Rate Interface (PRI)  Channelized T1/E1 Network Module 

			,io-2fe-tx-isl(1150)		-- I/O card Dual 10/100 Fast Ethernet ISL card for the 7100 series
			,ism-ipsec-mppe(1151)		-- Integrated Service Module, used only in slot 5 of the 7100 series, is a hardware accelerator for IPSEC Encryption and Compression, and MPPE encryption.
			,vpn-accelerator(1152)		-- VPN Encryption Accelerator Engine
			,vpn-accelerator-module2(1153)	-- VPN Encryption Accelerator Engine 2
			,vpn-accelerator-AES(1154)	-- VPN Encryption Accelerator Engine with AES Support
			,cre-rp(1180)			-- Central Routing Engine - Route Processor for Cisco 10000 series
			,cpu-as5400(1182)		-- CPU card for AS5400
			,cpu-mc3810-v3(1185)		-- CPU card for the MC3810-V3; higher performance than MC3810 with NEBs compliant changes.
			,cpu-7200-nse1(1186)		-- CPU card for use in the 7200 series, Network Service Engine 1.  Contains a PXF (Parallel Express Forwarding) processor to accelerate layer 3-7 IP features.
			,cpu-as5850(1187)			-- CPU card for AS5850 
			,cpu-7200-npe400(1188)		-- Network processing engine (CPU card) for 7200 series 
			,cpu-7150(1191)			-- CPU for the 7150 series
			,cpu-7401-nse(1193)		-- Cisco 7401 Network Processing Engine 
			,cpu-gsr-prp1(1196)		-- GSR Performance Route Processor 1 
			,cpu-7200-npeg1(1203)		-- Network Processing Engine (CPU card) for 7200VXR series
			,cpu-c2691-2fe(1204)		-- c2691 Motherboard with Fast Ethernet 
			,cpu-c3745-2fe(1205)		-- c3745 Motherboard with Fast Ethernet 
			,cpu-c3725-2fe(1206)		-- c3725 Motherboard with Fast Ethernet 
			,cpu-c3631-1fe(1207)		-- c3631 Motherboard with Fast Ethernet 
			,cpu-6400-nsp(1209)             -- Cisco 6400 Node Switch Processor
                        ,cpu-6400-nrp(1210)             -- Cisco 6400 Node Route Processor
                        ,cpu-6400-nrp2(1211)            -- Cisco 6400 Node Route Processor 2
                        ,cpu-6400-nrp2-sv(1212)         -- Cisco 6400 Node Route Processor 2 with Shaped VCs
			,cpu-as5400-hpx(1217)		-- CPU card for AS5400HPX
			,cpu-vg224(1224)		-- Line Side Analog Gateway with 24FXS Analog ports
			,cpu-gsr-prp2(1228)		-- GSR Performance Route Processor 2
			,cpu-c2801-2fe(1239)			-- 2801 Motherboard with two integrated fast ethernets

			,acc-24fe-tx(1307)		-- c10720 24 ports fast ethernet Tx access card
			,acc-24fe-fx-mm(1308)		-- c10720 24 ports fast ethernet FX MM (2km) access card
			,acc-24fe-fx-sm(1309)		-- c10720 24 ports fast ethernet FX SM (15km) access card
			,srp-oc48-sr(1310)		-- c10720 1 port OC-48c SRP SM short reach uplink card
			,srp-oc48-ir(1311)		-- c10720 1 port OC-48c SRP SM intermediate reach uplink card
			,atm-4oc3(1313)			-- 4 port OC3 ATM line card with single mode, intermediate reach optics for the C10000 platform
			,acc-4ge8fe-tx(1323)		-- c10720 4 port gigabit ethernet + 8 port fast ethernet access card 
			,acc-4ge8fe-fx-mm(1324)		-- c10720 4 port gigabit ethernet + 8 port fast ethernet FX MM (2km) access card 
			,acc-4ge8fe-fx-sm(1325)		-- c10720 4 port gigabit ethernet + 8 port fast ethernet FX SM (15km) access card 
			,ul-srp48-lr1(1326)		-- c10720 1 port OC-48c SRP SM Long Reach (40Km) uplink card
			,ul-srp48-lr2(1327)		-- c10720 1 port OC-48c SRP SM Long Reach (80Km) uplink card
			,c10720-mnt(1330)		-- C10720 Maintenance card
			,ul-pos-srp48-sm-sr(1332)	-- c10720 OC-48c POS/SRP SM short reach uplink card
			,ul-pos-srp48-sm-ir(1333)	-- c10720 OC-48c POS/SRP SM intermediate reach uplink card
			,ul-pos-srp48-sm-lr1(1334)	-- c10720 OC-48c POS/SRP SM Long Reach (40Km) uplink card
			,ul-pos-srp48-sm-lr2(1335)	-- c10720 OC-48c POS/SRP SM Long Reach (80Km) uplink card
			,acc-24fe-tx-b(1336)		-- c10720 24 ports fast ethernet Tx access card revB.
			,acc-4ge8fe-tx-b(1337)		-- c10720 4 port gigabit ethernet + 8 port fast ethernet access card revB.
			,ul-rpr-srp-48(1339)		-- c10720 1 port RPR(802.17)/SRP OC48 uplink card


			,as5400-dfc-carrier(1350)	-- Carrier card that holds Dial Feature Cards for the AS5400 platform
			,as5400-dfc-np348(1351)		-- Nextport (np) Modem Dial Feature Card consisting of 3 modem modules, 2 of which have 120 modems and that has 108, for a total of 348 modems per card, used in AS5400 and AS5350 platforms
			,as5400-dfc-np192(1352)		-- Nextport (np) Modem Dial Feature Card consisting of 2 modem modules, 1 of which has 120 modems the other 72, for a total of 192 modems per card, used in AS5400 and AS5350 platforms
	
			,dfc-8ce1(1450)			-- 8 Primary Rate Interface (PRI) Channelized E1 (ce1) Dial Feature Card used in AS5400 and AS5800 platforms 
			,dfc-8ct1(1451)			-- 8 Primary Rate Interface (PRI) Channelized T1 (ct1) Dial Feature Card used in AS5400 and AS5800 platforms 
			,dfc-ct3(1452)			-- Channelized T3 (ct3) Dial Feature Card used in AS5400 and AS5800 platforms
			,dfc-np108(1453)		-- Nextport (np) Modem Dial Feature Card consisting of 3 modem modules, each module has 36 modems, for a total of 108 modems per card, used in AS5400 and AS5800 platforms
			,isa-ipsec-mppe(1454)		-- Integrated Service Port Adapter, used in the 7100 and 7200 series as a module, and in the 7500 series as a Port Adapter.  Hardware Accelerator for IPSEC Encryption and Compression, and MPPE encryption.  May not be used in slot 5 of the 7100. 
			,wic-dslsar-20150(1455)		-- DSLSAR ADSL WIC (Wan Interface Card) used in 1720, 1750, 2600 and 3600 series.  DSLSAR - SAR (Segmentation & Reassembly) of ATM cells and can be used with any DSL (Digital Subscriber Line). Uses ADSL (Asymmetric Digital Subscriber Line) as the physical layer. 
			,wvic-2dsu-t1-dir(1462)		-- WAN Voice Interface Cards with a dual port T1 DSU with drop & insert and protection switching relay for MWR1900
			,wvic-2dsu-e1-dir(1463)		-- WAN Voice Interface Cards with a dual port E1 DSU with drop & insert and protection switching relay for MWR1900
			,vic-4vp-fxs-did(1464)		-- 4 port Voice Interface Card; Each port can function as Foreign Exchange Station(FXS) or Direct Inward Dialing (DID) Voice Port
			,vic-4fxo-us-m1(1465)		-- Four port Foreign Exchange Office Voice Interface Card for US/North America or M1 interface
			,vic-4fxo-m2-m3(1466)		-- Four port Foreign Exchange Office Voice Interface Card for M2 or M3 interface (software selectable on a card basis)
			,vic-4fxo-cama(1467)		-- Four port Foreign Exchange Office Voice Interface Card for US/North America with CAMA (Centralized Automated Message Accounting) 911 signalling support (software selectable per port basis)
			,nm-se(1477)			-- service engine network module
			,aim-se(1478)			-- service engine Advanced Interface Module
			,wic-se(1479)			-- service engine WIC
			,spa-4p-fe-7304(1495)		-- 4-port 10/100 Ethernet Shared Port Adapter (SPA-4FE-7304)
			,spa-2p-ge-7304(1496)		-- 2-port 10/100/1000 Ethernet Shared Port Adapter (SPA-2GE-7304)


			,cat6k-wsx-sup-12ge(1502)	-- Supervisor with 2 Gigabit Ethernet ports for the Catalyst 6000 series 
			,cat6k-wsx-6408-gbic(1503)	-- Card with 8 Gigabit Ethernet ports for the Catalyst 6000 series 
			,cat6k-wsx-6224-100fx-mt(1504)	-- Card with 24 port 100BaseFX MM (MT-RJ) for the Catalyst 6000 series
			,cat6k-wsx-6248-rj45(1505)	-- Card with 48 10/100 RJ45 Fast Ethernet ports for the Catalyst 6000 series 
			,cat6k-wsx-6248-tel(1506)	-- Card with 48 10/100 RJ21 Fast Ethernet ports for the Catalyst 6000 series 
			,cat6k-wsx-6302-msm(1507)	-- Multilayer Switch Module for the Catalyst 6000 series
			,cat6k-wsx-6024-mtrj(1509)	-- Card with 24 10/100 MTRJ Fast Ethernet ports for the Catalyst 6000 series
			,cat6k-msfc2(1510)		-- Multilevel Switching Feature Card Version 2 for the Catalyst 6000 series
			,cat6k-wsx-6316-ge-tx(1511)		-- 16-port RJ-45 Gigabit ethernet module
			,cat6k-wsx-6416-gbic(1512)		-- 16-port GBIC Gigabit ethernet module
			,cat6k-wsx-6324-100fx(1513)		-- 24-port 100FX multimode MT-RJ with 128K per-port packet buffer
			,cat6k-wsx-6348-rj45(1514)		-- 48-port 10/100 ethernet module
			,cat6k-wsx-6502-10ge(1515)		-- 10 Gigabit Ethernet Base Module
			,cat6k-wsx-6066-slb-apc(1516)		-- Venus: Server Load Balancing Application Processor Complex
			,cat6k-wsx-6548-rj45(1518)		-- 48 port 10/100 Hydra2+/Hydra2V+
			,cat6k-wsx-6248a-tel(1519)		-- Card for C6K with 48 10/100 RJ21 ports with enhanched QoS a.k.a Indus w/ Enhanced QoS
			,cat6k-wsx-sup2-2ge(1520)		-- Supervisor 2 with 2 Gigabit Ethernet ports
			,cat6k-wsc-6500-sfm(1521)		-- Catalyst 6500 Switch Fabric Module
			,cat6k-wsc-6500-sfm2(1522)		--Catalyst 6500 Switch Fabric Module II
			,cat6k-wsx-6816-gbic(1523)		-- Catalyst 6500 16 port 1000BaseX (Layer 3)
			,cat6k-wsx-6348-rj21(1528)	-- Catalyst 6500 48 port 10/100BaseTX (RJ-21)
			,cat6k-wsx-6516-gbic(1529)	-- Catalyst 6500 16 port 1000BaseX GBIC
			,cat6k-wsx-sup1a-2ge(1530)	-- Catalyst 6500 2 port 1000BaseX Supervisor module (GBIC)
			,cat6k-wsx-6548-rj21(1531)	-- Catalyst 6500 48 port 10/100BaseTX (RJ-21)
			,cat6k-wsx-6416-gemt(1532)	-- Catalyst 6500 16 port 1000BaseSX (MT-RJ)
			,cat6k-wsx-6380-nam(1533)	-- Catalyst 6500 Network Analysis Module
			,cat6k-wsx-6248a-rj45(1534)	-- Catalyst 6500 48 port 10/100BaseTX (RJ-45)
			,cat6k-wsx-6408a-gbic(1535)	-- Catalyst 6500 8 port 1000BaseX (GBIC), Enhanced QoS module
			,cat6k-wsx-6381-ids(1536)	-- Catalyst 6500 Intrusion Detection module
			,cat6k-wsx-6524-mmmt(1537)	-- Catalyst 6500 24 port 100BaseX MM (MT-RJ) module
			,cat6k-wsx-6516-getx(1538)	-- Catalyst 6500 16 port 10/100/1000BaseT (RJ-45) module 
			,cat6k-wsx-6501-10gex4(1539)	-- Catalyst 6500 1 port 10 Gigabit Ethernet (EX4) module
			,cat6k-wsf-6kvpwr(1541)		-- Catalyst 6500 inline power card 
                        ,cat6k-ws-svc-nam1(1542)        -- Catalyst 6500 Network Analysis Module
                        ,cat6k-ws-svc-nam2(1543)        -- Catalyst 6500 Network Analysis Module
                        ,cat6k-ws-svc-fwm1(1544)        -- Catalyst 6500 Firewall Module
                        ,cat6k-ws-svc-ssl1(1545)        -- Catalyst 6500 SSL Module
                        ,cat6k-wsx-6516a-gbic(1546)     -- Catalyst 6500 16 port 1000BaseX (GBIC) 
			,ipsec-vpnsm(1549)		-- Gigabit IPsec VPN Service Module for the Catalyst 6500 and 7600
			,dspm-pvdm3(1556)		-- Packet Voice DSP module with 3 C549 DSP's used by 17x0, 26x0, and 36x0 platforms
			,dspm-pvdm1(1561)		-- Packet Voice DSP module with 1 C549 DSP used by 17x0, 26x0, and 36x0 platforms
			,dspm-pvdm2(1562)		-- Packet Voice DSP module with 2 C549 DSPs used by 17x0, 26x0, and 36x0 platforms
			,dspm-pvdm4(1563)		-- Packet Voice DSP module with 4 C549 DSPs used by 17x0, 26x0, and 36x0 platforms
			,dspm-pvdm5(1564)		-- Packet Voice DSP module with 5 C549 DSPs used by 17x0, 26x0, and 36x0 platforms
			,hda-em-4dsp(1590)		-- 4-C5421 DSP Daughtercard
			,hda-em-10fxs(1591)		-- 10-port FXS Voice Interface Daughtercard
			,wic-sh-dsl(1565)		-- A WIC (Wan Interface Card) providing Symmetrical HIgh bit rate Digital Subscriber line (SHDSL) for 2600, 3620, 3640 and 3660 platforms 
			,hdv-8fxs(1566)			-- 8-Port FXS Voice Interface Daughtercard
			,hdv-4dsp(1567)			-- 4-chip DSP Daughtercard
			,vic-4vp-fxs-4did(1573)	-- 4-port Direct Inward Dialing (DID) and 4-port Foreign Exchange Station (FXS) Voice Interface Daughtercard
			,em-4fxs-4fxo(1581)		-- 8-port voice/fax expansion module - 4FXS/4FXO
			,em-6fxo(1582)			-- 6-port voice/fax expansion module - FXO
			,em-4bri-nt-te(1583)		-- 4-port voice/fax expansion module - BRI
			,vic2-mft1-t1e1(1594)		-- 1-Port RJ-48 Multiflex Voice Trunk - T1/E1
			,vic2-mft2-t1e1(1595)		-- 2-Port RJ-48 Multiflex Voice Trunk - T1/E1
			,em2-hda-4fxo(1596)		-- 4-port voice/fax expansion module - FXO
			,vic-1j1(1597)			-- VIC-1J1,Digital Voice J1 Interface with a single port DB-15 Connector for 2600, 3600 and 3700 series
			,wic-1am-v2(1598)		-- WAN Interface Card - 1 Port Analog Modem
			,wic-2am-v2(1599)		-- WAN Interface Card - 2 port Analog Modem

			,ituc-1p8(1611)			-- ITU-C octal-line module 
			,atuc-1p8-dmt(1618)		-- ATU-C octal-line DMT module
			,stuc-1p8(1619)			-- STU-C octal-line module
			,atuc-1p8-dmt-itemp(1620)	-- ATU-C octal-line DMT module industrial temperature grade
			,stuc-1p8-itemp(1621)		-- STU-C octal-line shdsl module industrial temperature grade
			,cva122(1700)		--  Cisco CVA122 Cable Voice Adapter (Residential Cable Modem with two Voice Ports)
			,cva124(1701)		--  Cisco CVA124 Cable Voice Adapter (Residential Cable Modem with four Voice Ports)
			,cva122e(1702)		--  Cisco CVA122 Cable Voice Adapter (Residential Cable Modem with two voice ports) - European version
			,cva124e(1703)		--  Cisco CVA124 Cable Voice Adapter (Residential Cable Modem with four voice ports) - European version
			,as5850-epm-2ge(1750)	-- Route Switch Controller Card with 2 port Gigabit Ethernet 
			,as5850-ct3-216up(1751)	-- Feature Card with Channelized T3 and 216 Universal Ports
			,as58xx-324up(1753)	-- Feature Card with 324 Universal Ports 
			,as5850-24e1(1754)      -- Feature Card with 24 port Channelized E1 for the AS5850 platform


			,gsr-16oc3-chstsds3-sm-ir-sc(1900)	--  GSR 16 port OC3 channelized to STS-3c/STM-1 or DS-3; Single Mode fiber, Intermediate Reach, SC connector line card
			,gsr-16oc3-chstsds3-sm-lr-sc(1901)	--  GSR 16 port OC3 channelized to STS-3c/STM-1 or DS-3; Single Mode fiber, Long Reach, SC connector line card
			,gsr-2oc3-chds1(1905)	-- GSR platform card, 2 ports of OC3 (Sonet/SDH); each port is channelized to DS1 level
			,ssrp-oc192-sm-lr(1906)	-- GSR 1 port SONET based SRP OC-192c/STM-64 single mode long reach line card
			,ssrp-oc192-sm-ir(1907)	-- GSR 1 port SONET based SRP OC-192c/STM-64 single mode intermediate reach line card
			,ssrp-oc192-sm-sr(1908)	-- GSR 1 port SONET based SRP OC-192c/STM-64 single mode short reach line card 
			,ssrp-oc192-sm-vsr(1909)	-- GSR 1 port SONET based SRP OC-192c/STM-64 single mode very short reach line card 
			,gsr-sfc10(1912)		-- GSR Switch Fabric Card for 12010
			,gsr-csc10(1913)		-- Clock Scheduler Card for GSR 12010
			,gsr-alarm10(1914)		-- GSR Alarm module
			,gsr-bus-board10(1915)		-- GSR Bus Board for Power distribution
			,gsr-oc48-chstsds3-sm-sr-sc(1916)	-- GSR 1-port-OC48, channelized to to STS-48c/STM-16, STS-12c/STM-4, STS-3c/STM-1 or DS3, single mode, short-reach, SC connector
			,gsr-e48-pos-oc48-sm-sr-sc(1917)	-- GSR, Edge Engine 48, (concatenated) 1 port OC48 POS, single mode, short-reach, SC connector
			,gsr-e48-pos-oc48-sm-lr-sc(1918)	-- GSR, Edge Engine 48, (concatenated) 1 port OC48 POS, single mode, short-reach, SC connector
			,gsr-e48-pos-qoc12-sm-ir-sc(1919)	-- GSR, Edge Engine 48, 4 port (concatenated) OC12 POS, single mode, intermediate reach, SC connector
			,gsr-e48-pos-16oc3-sm-ir-sc(1920)	-- GSR, Edge Engine 48, 16 port (concatenated) OC3 POS, single mode, intermediate reach, SC connector 
			,copper-6e3(1921)		-- GSR 6 port copper E3 interface line card
			,copper-12e3(1922)		-- GSR 12 port copper E3 interface line card
			,gsr-e48-pos-16oc3-sm-ir-lc(1926)       -- GSR, Edge Engine 48, 16 port (concatenated) OC3 POS, single mode, intermediate reach, LC connector
			,gsr-16oc3-chstsds3-sm-ir-lc(1927)      -- GSR 16 port OC3 channelized to STS-3c/STM-1 or DS-3; single mode fiber, intermediate reach, LC connector
			,gsr-sfc6(1929)			-- GSR 12406 Switch Fabric Card
			,gsr-csc6(1930)			-- GSR 12406 Clock Scheduler Card
			,gsr-alarm6(1931)		-- GSR 12406 Alarm Module
			,pos-en-qoc48-vsr(1932)		-- GSR enhanced 4 Port Packet Over Sonet OC-48, Very Short Reach Card
			,pos-en-qoc48-mm-sr-sc(1933)	-- GSR enhanced 4 Port Packet Over Sonet OC-48, Multi Mode, Short Reach, SC Connector Card
			,pos-en-qoc48-sm-ir-sc(1934)	-- GSR enhanced 4 Port Packet Over Sonet OC-48, Single Mode, Intermediate Reach, SC Connector Card
			,pos-en-qoc48-sm-ir-fc(1935)	-- GSR enhanced 4 Port Packet Over Sonet OC-48, Single Mode, Intermediate Reach, FC Connector Card
			,pos-en-qoc48-sm-vlr-sc(1936)	-- GSR enhanced 4 Port Packet Over Sonet OC-48, Single Mode, Very Long Reach, SC Connector Card
			,pos-en-qoc48-sm-vlr-fc(1937)	-- GSR enhanced 4 Port Packet Over Sonet OC-48, Single Mode, Very Long Reach, FC Connector Card
			,pos-en-qoc48-sm-elr-sc(1938)	-- GSR enhanced 4 Port Packet Over Sonet OC-48, Single Mode, Extremely Long Reach, SC Connector Card
			,pos-en-qoc48-sm-elr-fc(1939)	-- GSR enhanced 4 Port Packet Over Sonet OC-48, Single Mode, Extremely Long Reach, FC Connector Card
			,pos-en-oc192-vsr(1940)		-- GSR enhanced 1 Port Packet Over Sonet OC-192, Very Short Reach Card
			,pos-en-oc192-sm-sr2-sc(1941)	-- GSR enhanced 1 Port Packet Over Sonet OC-192, Single Mode, Short Reach 2, SC Connector Card
			,pos-en-oc192-sm-sr2-fc(1942)	-- GSR enhanced 1 Port Packet Over Sonet OC-192, Single Mode, Short Reach 2, FC Connector Card
			,pos-en-oc192-sm-vlr-sc(1943)	-- GSR enhanced 1 Port Packet Over Sonet OC-192, Single Mode, Very Long Reach, SC Connector Card
			,pos-en-oc192-sm-vlr-fc(1944)	-- GSR enhanced 1 Port Packet Over Sonet OC-192, Single Mode, Very Long Reach, FC Connector Card
			,pos-en-oc192-sm-elr-sc(1945)	-- GSR enhanced 1 Port Packet Over Sonet OC-192, Single Mode, Extremely Long Reach, SC Connector Card
			,pos-en-oc192-sm-elr-fc(1946)	-- GSR enhanced 1 Port Packet Over Sonet OC-192, Single Mode, Extremely Long Reach, FC Connector Card
			,gsr-sfc12410(1947)		-- GSR 12410 Switch Fabric Card
			,gsr-csc12410(1948)		-- GSR 12410 Clock Scheduler Card
			,iad2420-vm-8fxs(1950)			-- This card provides 8 analog Foreign eXchange Stations (FXS) in the Integrated Access Device 2420 (IAD2420) chassis
			,iad2420-16fxs(1951)			-- This card provides 16 analog Foreign eXchange Stations (FXS) in the Integrated Access Device 2420 (IAD2420) chassis
			,iad2420-vm-pwr(1952)			-- This card provides power supply to high density analog FXS voice module in the Integrated Access Device 2420 (IAD2420) chassis
			,iad2420-adsl(1953)			-- This card provides access to ADSL (Asymmetrical Digital Subscriber Line) over ATM (Asynchronous Transfer Mode) AAL2 (ATM Adaptation Layer 2), AAL5 (ATM Adaptation Layer 5) and various class of QoS (Quality of Service) for both voice and data service on the Integrated Access Device 2420 (IAD2420) chassis
			,iad2420-hcm1(1954)			-- High performance compression module for the IAD2420 platform equipped with one TI 549 DSP
			,iad2420-hcm2(1955)			-- High performance compression module for the IAD2420 platform equipped with two TI 549 DSPs
			,iad2420-hcm3(1956)			-- High performance compression module for the IAD2420 platform equipped with three TI 549 DSPs
			,iad2420-hcm4(1957)			-- High performance compression module for the IAD2420 platform equipped with four TI 549 DSPs
			,iad2420-hcm5(1958)			-- High performance compression module for the IAD2420 platform equipped with five TI 549 DSPs
			,iad2420-hcm6(1959)			-- High performance compression module for the IAD2420 platform equipped with six TI 549 DSPs
			,iad2420-cpu(1960)			-- CPU card for IAD2420
			,iad2420-mfm-e1-unbalanced(1961)	-- IAD2420 E1 75 ohms unbalanced
			,iad2420-mfm-e1-dsx1-csu(1962)		-- IAD2420 E1 100/120 ohms balanced
			,iad2420-mfm-t1-dsx1-csu(1963)		-- IAD2420 T1 100/120 ohms balanced only
			,iad2420-8fxo(1964)			--  High density 8 analog Foreign eXchange Office (FXO) module
			,iad2420-16fxs-off-premise(1967)	-- IAD2420 Sixteen FXS Off Premise Analog Voice Module 
			,gsr-atm-en-8oc3-mm(1968)		-- GSR enhanced 8 port OC3c/STM-1 Multimode ATM LC
			,iad2430-ob-8fxs(1983)			-- This card provides 8 on-board analog Foreign Exchange Stations (FXS) in the Integrated Access Device 2430 (IAD2430) chassis
			,iad2430-ob-16fxs(1984)			-- This card provides 16 on-board analog Foreign Exchange Stations (FXS) in the Integrated Access Device 2430 (IAD2430) chassis
			,iad2430-ob-24fxs(1985)			-- This card provides 24 on-board analog Foreign Exchange Stations (FXS) in the Integrated Access Device 2430 (IAD2430) chassis
			,iad2430-ob-t1e1(1986)			-- This card provides on-board T1/E1 in the Integrated Access Device 2430 (IAD2430) chassis.

			,mc3810-hcm5(2000)			--  High performance compression module for the MC3810 platform equipped with five TI 549 DSPs
			,m10000base-lx4(2051)			--  Cisco Wide-WDM 1310nm Laser 10 gigabit ethernet port adapter 
			,m10000base-ex4(2052)			--  Cisco Wide-WDM 1550nm Laser 10 gigabit ethernet port adapter 
			,m10000base-lr(2053)			--  Cisco Serial 1310nm Laser 10 gigabit ethernet port adapter 
			,m10000base-er(2054)			-- Cisco Serial 1550nm Laser 10 gigabit ethernet port adapter 
			,m10000base-sx4(2055)			-- Cisco Wide-WDM 850nm Laser 10 gigabit ethernet port adapter 

			,c7401(2100)				-- Cisco 7400 Family, 1 Slot Router
			,io-c7401-ge(2101)			-- Cisco 7401 I/O Controller with dual 10/100/1000Mbps GE interfaces
			,c7411-npeg1(2128)			-- Cisco 7400 Family, 1 Slot Router
			,io-c7411-ge(2129)			-- Cisco 7411 I/O Controller with three 10/100/1000Mbps GE interfaces
			,vip6-80(2132)				-- A new VIP card to be used in 7500 box. this card is same as VIP4-80 but with a higher speed CPU.
			,c7300-cc-pa(2138)			-- Port Adaptor Carrier Card for Cisco 7304

			,gsr-e48-pos-oc48-sm-ir-sc(2201)	-- GSR, Edge Engine, OC48 POS, Single Mode, Intermediate Reach, SC Connector
			,gsr-e-oc192-sm-lr-sc(2203)		-- GSR Edge 1 Port Packet over Sonet OC-192, Single Mode, Long Reach, SC Connector card
			,gsr-e-oc192-sm-vsr-sc(2204)		-- GSR Edge 1 Port Packet over Sonet OC-192, Single Mode, Very Short Reach, SC Connector card
			,gsr-e-oc192-sm-vsr-fc(2205)		-- GSR Edge 1 Port Packet over Sonet OC-192, Single Mode, Very Short Reach, FC Connector card
			,gsr-e-oc192-sm-sr-fc(2206)		-- GSR Edge 1 Port Packet over Sonet OC-192, Single Mode, Short Reach, FC Connector card
			,gsr-e-oc192-sm-sr-sc(2207)		-- GSR Edge 1 Port Packet over Sonet OC-192, Single Mode, Short Reach, SC Connector card
			,gsr-e-oc192-sm-lr-fc(2208)		-- GSR Edge 1 Port Packet over Sonet OC-192, Single Mode, Long Reach, FC Connector card
			,gsr-e-qoc48-sm-lr-fc(2209)		-- GSR Edge 4 Port Packet over Sonet OC-48, Single Mode, Long Reach, FC Connector card
			,gsr-e-qoc48-sm-lr-sc(2210)		-- GSR Edge 4 Port Packet over Sonet OC-48, Single Mode, Long Reach, SC Connector card
			,gsr-e-qoc48-sm-vsr-sc(2211)		-- GSR Edge 4 Port Packet over Sonet OC-48, Single Mode, Very Short Reach, SC Connector card
			,gsr-e-qoc48-sm-vsr-fc(2212)		-- GSR Edge 4 Port Packet over Sonet OC-48, Single Mode, Very Short Reach, FC Connector card
			,gsr-e-qoc48-sm-sr-fc(2213)		-- GSR Edge 4 Port Packet over Sonet OC-48, Single Mode, Short Reach, FC Connector card
			,gsr-e-qoc48-sm-sr-sc(2214)		-- GSR Edge 4 Port Packet over Sonet OC-48, Single Mode, Short Reach, SC Connector card
			,gsr-e-qoc48-vsr(2215)			-- GSR Edge 4 Port Packet over Sonet OC-48, Very Short Reach
			,gsr-e-qoc48-sm-sr2-sc(2216)		-- GSR Edge 4 Port Packet over Sonet OC-48, Single Mode, Short Reach 2, SC Connector card
			,gsr-e-qoc48-sm-sr2-fc(2217)		-- GSR Edge 4 Port Packet over Sonet OC-48, Single Mode, Short Reach 2, FC Connector card
			,gsr-e-qoc48-mm-sr-sc(2218)		-- GSR Edge 4 Port Packet over Sonet OC-48, Multi Mode, Short Reach, SC Connector card
			,gsr-e-qoc48-sm-ir-sc(2219)		-- GSR Edge 4 Port Packet over Sonet OC-48, Single Mode, Intermediate Reach, SC Connector card
			,gsr-e-qoc48-sm-ir-fc(2220)		-- GSR Edge 4 Port Packet over Sonet OC-48, Single Mode, Intermediate Reach, FC Connector card
			,gsr-e-qoc48-sm-vlr-sc(2221)		-- GSR Edge 4 Port Packet over Sonet OC-48, Single Mode, Very Long Reach, SC Connector card
			,gsr-e-qoc48-sm-vlr-fc(2222)		-- GSR Edge 4 Port Packet over Sonet OC-48, Single Mode, Very Long Reach, FC Connector card
			,gsr-e-qoc48-sm-elr-sc(2223)		-- GSR Edge 4 Port Packet over Sonet OC-48, Single Mode, Extremely Long Reach, SC Connector card
			,gsr-e-qoc48-sm-elr-fc(2224)		-- GSR Edge 4 Port Packet over Sonet OC-48, Single Mode, Extremely Long Reach, FC Connector card
			,gsr-e-oc192-vsr(2225)			-- GSR Edge 1 Port Packet over Sonet OC-192, Very Short Reach
			,gsr-e-oc192-sm-sr2-sc(2226)		-- GSR Edge 1 Port Packet over Sonet OC-192, Single Mode, Short Reach 2, SC Connector card
			,gsr-e-oc192-sm-sr2-fc(2227)		-- GSR Edge 1 Port Packet over Sonet OC-192, Single Mode, Short Reach 2, FC Connector card
			,gsr-e-oc192-mm-sr-sc(2228)		-- GSR Edge 1 Port Packet over Sonet OC-192, Multi Mode, Short Reach, SC Connector card
			,gsr-e-oc192-sm-ir-sc(2229)		-- GSR Edge 1 Port Packet over Sonet OC-192, Single Mode, Intermediate Reach, SC Connector card
			,gsr-e-oc192-sm-ir-fc(2230)		-- GSR Edge 1 Port Packet over Sonet OC-192, Single Mode, Intermediate Reach, FC Connector card
			,gsr-e-oc192-sm-vlr-sc(2231)		-- GSR Edge 1 Port Packet over Sonet OC-192, Single Mode, Very Long Reach, SC Connector card
			,gsr-e-oc192-sm-vlr-fc(2232)		-- GSR Edge 1 Port Packet over Sonet OC-192, Single Mode, Very Long Reach, FC Connector card
			,gsr-e-oc192-sm-elr-sc(2233)		-- GSR Edge 1 Port Packet over Sonet OC-192, Single Mode, Extremely Long Reach, SC Connector card
			,gsr-e-oc192-sm-elr-fc(2234)		-- GSR Edge 1 Port Packet over Sonet OC-192, Single Mode, Extremely Long Reach, FC Connector card
			,ssrp-2oc48-srp-sm-sr-lc(2236)		-- GSR 2 port SONET dual SRP/POS OC-48c/STM-16, SRP Mode, Single Mode, Short Reach, LC Connector card
			,ssrp-2oc48-srp-sm-ir-lc(2237)		-- GSR 2 port SONET dual SRP/POS OC-48c/STM-16, SRP Mode, Single Mode, Intermediate Reach, LC Connector card
			,ssrp-2oc48-srp-sm-lr-lc(2238)		-- GSR 2 port SONET dual SRP/POS OC-48c/STM-16, SRP Mode, Single Mode, Long Reach, LC Connector card
			,ssrp-2oc48-pos-sm-sr-lc(2239)		-- GSR 2 port SONET dual SRP/POS OC-48c/STM-16, POS Mode, Single Mode, Short Reach, LC Connector card
			,ssrp-2oc48-pos-sm-ir-lc(2240)		-- GSR 2 port SONET dual SRP/POS OC-48c/STM-16, POS Mode, Single Mode, Intermediate Reach, LC Connector card
			,ssrp-2oc48-pos-sm-lr-lc(2241)		-- GSR 2 port SONET dual SRP/POS OC-48c/STM-16, POS Mode, Single Mode, Long Reach, LC Connector card
			,gsr-gefe(2244)				-- Modular Gigabit/Fast Ethernet card for GSR 
			,gsr-pa-3ge(2246)			-- 3 Port Gigabit Ethernet Port Adapter Of Modular Gigabit/Fast Ethernet card for GSR 
			,gsr-pa-24fe(2247)			-- 24 Port Fast Ethernet Port Adapter Of Modular Gigabit/Fast Ethernet card for GSR 
			,gsr-e48-atm-4oc12-sm-ir-sc(2248)	-- Edge Engine 48, ATM, 4 ports OC12/STM4, Single Mode, Intermediate Reach, SC connector
			,gsr-e48-atm-4oc12-mm-sr-sc(2249)	-- GSR, Edge Engine 48, ATM, 4 ports OC12/STM4, Multi Mode, Short Reach, SC connector
			,ssrp-e48-2oc12-sm-ir(3008)		-- GSR 2 port SONET based SRP OC-12c/STM-4 Single mode Intermediate reach line card 
			,ssrp-e48-2oc12-sm-xr(3009)		-- GSR 2 port SONET based SRP OC-12c/STM-4 Single mode Extented reach line card 
			,ssrp-e48-1oc12-sm-ir(3010)		-- GSR 1 port SONET based SRP OC-12c/STM-4 Single mode Intermediate reach line card 
			,ssrp-e48-1oc12-sm-xr(3011)		-- GSR 1 port SONET based SRP OC-12c/STM-4 Single mode Extented reach line card 
			,gsr-6ds3e3-smb(3028)			-- GSR 6 Port DS3/E3 Clear Channel, SMB Connector line card
			,gsr-6ds3e3ct3-smb(3029)		-- GSR 6 Port DS3/E3 Clear channel and/or Channelized to DS1/E1, SMB Connector line card 
			,gsr-2oc3-chds1ds3e3-sm-ir-sc(3030)	-- GSR 2 Port STM-1/OC-3 Channelized to DS3/E3/DS1/E1, Single Mode, Intermediate Reach and SC Connector line card

			,vism-pr-8e1(3050)			-- Voice Interworking Service Module Premium Card (VISM-PR) with 8 E1 ports
			,vxsm-4oc3(3051)			-- Voice switch service module, 4 port OC3/STM-1 compliant
			,mgx-srm-4oc3(3052)			-- MGX88xx voice service redundancy module, used to providing 1:N redundancy for 4 OC3

			,hd-dsp(4015)				-- 5510 Digital Signal Processor on NM-HD-1V,NM-HD-2V and NM-HD-2VE
			,nm-8am-v2(4020)			--  8 Port Analog Modem Network Module Version 2
			,nm-16am-v2(4021)			--  16 Port Analog Modem Network Module Version 2  
			,cpu-c2811-2fe(4023)			--  2811 Motherboard with two integrated fast ethernets and integrated VPN
			,cpu-c2821-2ge(4024)			--  2821 Motherboard with two integrated gigabit ethets and integrated VPN
			,cpu-c2851-2ge(4025)			--  2851 Motherboard with two integrated gigabit ethernets and integrated VPN
			,hwic-serial4t(4026)			--  High Speed Wan Interface Card with 4 serial ports(HWIC-4T)
			,hwic-serial4as(4027)			--  High Speed Wan Interface Card with 4 low speed sync/async serial ports(HWIC-4A/S)
			,hwic-serial8as(4028)			--  High Speed Wan Interface Card with 8 low speed RS232 sync/async serial ports(HWIC-8A/S)
			,hwic-serial8a(4029)			--  High Speed Wan Interface card with 8 RS232 async port(HWIC-8A)
			,hwic-serial16a(4030)			--  High Speed Wan Interface card with 16 RS232 async ports(HWIC-16A)

			,cat6k-ws-sup720(4050)		-- Catalyst 6500 Supervisor Module 720 CPU board
			,cat6k-ws-sup720-base(4051)	-- Catalyst 6500 Supervisor Module 720 base board
			,cat6k-wsx-6802-10ge(4052)        -- Catalyst 6500 2 port 10 GE 
			,cat6k-wsx-6832-sfp(4053)        -- Catalyst 6500 32 port 1000Base FX (SFP GBIC) 
			,cat6k-wsx-6748-getx(4054)        -- Catalyst 6500 48 port 10/100/1000 (RJ-45) 
			,cat6k-wsx-6704-10ge(4055)        -- Catalyst 6500 4 port 10 GE 
			,cat6k-wsx-6748-sfp(4056)        -- Catalyst 6500 48 port 1000Base FX (SFP GBIC)
			,cat6k-wsx-6724-sfp(4057)        -- Catalyst 6500 24 port 1000Base FX (SFP GBIC)
			,cat6k-wsf-6k-pfc(4058)        --  Catalyst 6500 L3 switching engine 
			,cat6k-wsf-6k-pfc2(4059)        -- Catalyst 6500 L3 switching engine II  
			,cat6k-wsf-6k-dfc(4060)        -- Catalyst 6500 distributed switching engine 
			,cat6k-wsf-6k-pfc3a(4061)        -- Catalyst 6500 Centralized L3 switching engine IIIa
			,cat6k-wsf-6k-dfc3a(4062)        -- Catalyst 6500 Distributed L3 switching engine IIIa
			,cat6k-wsx-6148-ge-tx(4063)	-- Catalyst 6000 48 port10/100/1000BaseT(RJ-45) module 
			,cat6k-wsx-6148-rj21(4064)	-- Catalyst 6000 48 port10/100BaseTX(RJ-21) module 
			,cat6k-wsx-6148-rj45(4065)	-- Catalyst 6000 48 port10/100BaseTX(RJ-45) module 
			,cat6k-wsx-6548-getx(4066)	-- Catalyst 6500 48 port 10/100/1000 (RJ-45)
			,cat6k-wsf-6700-dfc3a(4067)	-- Catalyst 6500 Distributed L3 switching engine IIIa 
			,cat6k-wsx-6324-100fx-sm(4068)	-- 24-port 100FX single mode MT-RJ with 128K per-port packet buffer
			,cat6k-ws-svc-idsm2(4069)       -- Catalyst 6500 Intrusion Detection Module
			,cat6k-ws-svc-idsupg(4070)      -- Catalyst 6500 IDS 2 accelerator board
                        ,cat6k-wsx-6148x2-rj45(4071)      -- Catalyst 6500 96-port 10/100BaseTX (RJ-45) module
                        ,cat6k-wsf-6k-fe48x2-af(4072)   -- Catalyst 6500 Inline voice daughter card
			,cat6k-wsf-6k-fe48-af(4073)	-- Cat6k voice daughter cards 
			,cat6k-wsf-6k-ge48-af(4074)	-- Cat6k voice daughter cards
			,cat6k-wsf-6k-vpwr-ge(4075)	-- Cat6k voice daughter cards
			,cat6k-wsf-6700-cfc(4076)	-- Catalyst 6500 centralized Forwarding Card 
			,cat6k-ws-svc-wlan1-k9(4077)	-- Catalyst 6500 Wireless LAN module
			,cat6k-ws-sup32-ge(4079)	-- Catalyst 6500 Supervisor Module with 8 Gigabit Ethernet SFP uplink ports
			,cat6k-ws-sup32-10ge(4080)	-- Catalyst 6500 Supervisor Module with 2 10-GE uplink ports
			,cat6k-msfc2a(4081)	-- Multilevel Switching   Feature Card Version 2a for the Catalyst 6000 series
			,cat6k-ws-6340-sup(4082)	-- ME6340 Supervisor
			,cat6k-ws-6340-lca(4083)	-- ME6340 48 port ADSL 2/2+ Annex A Module
			,cat6k-ws-6340-lcb(4084)	-- ME6340 48 port ADSL 2/2+ Annex B Module
			,cat6k-wsx-6196-rj21(4091)	-- Catalyst 6500 96 port 10/100BaseTX (RJ-21) module
			,cat6k-wsx-6148-fe-sfp(4092)	-- Catalyst 6500 48 port 100Base-X SFP module
			,cat6k-wsx-6148a-getx(4093)	-- Catalyst 6500 48 port 10/100/1000BaseTX (RJ-45) module
			,cat6k-wsx-6148a-rj45(4094)	-- Catalyst 6500 48 port 10/100BaseTX (RJ-45) module
			,cat6k-wsg-6483(4095)	-- Catalyst 6500 10GE-ER Serial 1550nm extended reach module
			,cat6k-wsg-6485(4096)	-- Catalyst 6500 10GE-LX4 Campus 1310nm WWDM long haul/short reach module
			,cat6k-wsg-6488(4097)	-- Catalyst 6500 10GE-LR Serial 1310nm long haul module
			,cat6k-wsg-6489(4098)	-- Catalyst 6500 10GE-SX4 850nm WWDM short reach module

			,oc3-sfp(4100)			-- Oc3 Small Form Factor Pluggable Optics(SFP)
			,oc12-sfp(4101)			-- Oc12 Small Form Factor Pluggable Optics(SFP)
			,osm-2oc48-pos-ss(4102)		-- Optical Service Module, 2-Port OC48 POS, Single-mode, Short-reach with 4 Gigabit Ethernet ports
			,osm-2oc48-pos-si(4103)			-- Optical Service Module, 2-Port OC48 POS Single-mode, Intermediate-reach with 4 Gigabit Ethernet ports
			,osm-2oc48-pos-sl(4104)		-- Optical Service Module, 2-Port OC48 POS Single-mode, Long-reach with 4 Gigabit Ethernet ports
			,osm-1oc48-srp-ss(4105)		-- Optical Service Module, 1-Port OC48 SONET based SRP,Single-mode, Short-reach with 4 Gigabit Ethernet ports
			,osm-1oc48-srp-si(4106)		-- Optical Service Module, 1-Port OC48 SONET based SRP,Single-mode, Intermediate-reach with 4 Gigabit Ethernet ports
			,osm-1oc48-srp-sl(4107)		-- Optical Service Module, 1-Port OC48 SONET based SRP,Single-mode, Long-reach with 4 Gigabit Ethernet ports
			,pwr-ac-465w(4113)			-- Cisco 465W AC Power Supply.
			,oc192-xfp-smsr1(4128)			-- OC192 XFP Single Mode Short Reach 1 (2km)
			,oc192-xfp-smir2(4129)			-- OC192 XFP Single Mode Intermediate Reach 2 (40km)
			,oc192-xfp-smlr2(4130)			-- OC192 XFP Single Mode Long Reach 2 (80km)
			,cable50cm-sfp(4131)			-- SFP patch cable, 50cm (centimeters)
			,pwr-ac-125w(4132)			-- Cisco 125W AC Power Supply
			,pwr-ac-60w(4133)			-- Cisco 60W AC Power Supply
			,pwr-dsCAD-6000W(4138)			-- 6000W AC Power Supply
			,pwr-cat3750-ac210w12v(4139)			-- Cisco Catalyst 3750 AC power Supply  210 Watt, 12V DC
			,pwr-cat3750-ac375w48v(4140)			-- Cisco Catalyst 3750 AC power Supply  375 Watt, -48V DC
			,pwr-crs116-power-shelf-ac-delta(4141)			-- Cisco CRS-1 Series AC Delta Power Shelf for 16 Slots Line Card Chassis
			,pwr-crs116-power-shelf-ac-wye(4142)			-- Cisco CRS-1 Series AC Wye Power Shelf for 16 Slots Line Card Chassis
			,pwr-crs116-power-shelf-dc(4143)			-- Cisco CRS-1 Series DC Power Shelf for 16 Slots Line Card Chassis
			,pwr-crs116-ac-rectifier(4144)			-- Cisco CRS-1 Series AC Power Rectifier for 16 Slot Line Card Chassis and Fabric Card Chassis
			,pwr-crs116-dc-pem(4145)			-- Cisco CRS-1 Series DC Power Entry Module for 16 Slot Line Card Chassis and Fabric Card Chassis



			,hwic-dot11-bg(4221)			--  802.11 b/g Access Point until Jul 2004, contact pgiriraj
			,aim-vpn-bp(4223)			--  VPN Encryption Advanced Interface Module - Base Performance
			,aim-vpn-ep(4224)			--  VPN Encryption Advanced Interface Module - Enhanced Performance
			,nm-vpn-mp(4225)			--  VPN Encryption Network Module - Mid Performance
			,aim-vpn-hp(4226)			--  VPN Encryption Advanced Interface Module - High
			,aim-vpn-bp2(4227)			--  VPN Encryption Advanced Interface Module - Base Performance (version 2)
			,aim-vpn-ep2(4228)			--  VPN Encryption Advanced Interface Module - Enhanced Performance (version 2)
			,aim-vpn-hp2(4229)			--  VPN Encryption Advanced Interface Module - High Performance (version 2)
			,aim-vpn-bp2-plus(4230)			--  VPN Encryption Advanced Interface Module - Base Performance (version 2 Plus)
			,aim-vpn-ep2-plus(4231)			--  VPN Encryption Advanced Interface Module - Enhanced Performance (version 2 Plus)
			,aim-vpn-hp2-plus(4232)			--  VPN Encryption Advanced Interface Module - High Performance (version 2 Plus)
			,hwic-adsl-bri-pots(4233)			--  ADSL over POTS and BRI S/T
			,hwic-adsl-bri-isdn(4234)			--  ADSL over ISDN and BRI S/T
			,hwic-adsl-isdn(4235)			--  ADSL over ISDN
			,hwic-adsl-pots(4236)			--  ADSL over POTS
			,mds-ds-x9530-sf2-k9(4238)			--  DS-X9530-SF2-K9  - Sup-2, Supervisor/Fabric module
			,mds-ds-x9112(4239)			--  DS-X9112-  12-port Fibre Channel switching module
			,mds-ds-x9124(4240)			--  DS-X9124-  24-port Fibre Channel switching module
			,mds-ds-x9148(4241)			--  DS-X9148-  48-port Fibre Channel switching module
			,mds-ds-x9704(4242)			--  DS-X9704-  4-port Fibre Channel switching module
			,nm-cue-ec(4244)			--  Service Engine Network Module with 512MB RAM
			,mds-ds-13-slt-fab1(4245)			--  Cisco MDS 9513 Fabric 1 module
			,mds-ds-c9513-cl(4246)			--  Cisco MDS 9513 clock module - DS-C9513-CL
			,dfc-dl108(4247)			--  These cards are similar to DFC-NP108 and DFC-NP60 used on AS5400 platforms, but they are capable of only dial calls.
			,dfc-dl60(4248)			--  These cards are similar to DFC-NP108 and DFC-NP60 used on AS5400 platforms, but they are capable of only dial calls.



			,ce-scsi-2636(4357)			-- SCSI daughter card used by Content Engine Modules for 26xx and 36xx series platforms
			,ce-ide-2636(4358)			-- IDE  daughter card used by Content Engine Modules for 26xx and 36xx series platforms


			,wic-t1-csudsu-v2(4450)			--  Wan Interface Card with 1 Fractional T1 CSU/DSU port, version 2
			,crs14-oc192-ir-plim(4460)			-- Cisco CRS-1 Series 4xOC192/STM64 POS/DPT Interface Module/IR
			,spa-8x-ge(4461)			-- 8 Port Gigabit Ethernet Shared Port Adapter
			,wic-1-shdsl-v3(4465)			-- WAN Interface Card - ATM (With multi line G.SHDSL module)
			}
                   ACCESS  read-only
                   STATUS  deprecated
                   DESCRIPTION                           "Functional type of this card."
                   ::= { cardTableEntry 2 }

               cardDescr OBJECT-TYPE
                   SYNTAX  DisplayString
                   ACCESS  read-only
                   STATUS  deprecated
                   DESCRIPTION                           "Text description of this card."
                   ::= { cardTableEntry 3 }

               cardSerial OBJECT-TYPE
                   SYNTAX  INTEGER
                   ACCESS  read-only
                   STATUS  deprecated
                   DESCRIPTION                           "The serial number of this card, or zero if
                           unavailable."
                   ::= { cardTableEntry 4 }

               cardHwVersion OBJECT-TYPE
                   SYNTAX  DisplayString
                   ACCESS  read-only
                   STATUS  deprecated
                   DESCRIPTION                           "Hardware revision level of this card, or an
                           empty string if unavailable."
                   ::= { cardTableEntry 5 }

               cardSwVersion OBJECT-TYPE
                   SYNTAX  DisplayString
                   ACCESS  read-only
                   STATUS  deprecated
                   DESCRIPTION                           "Version of the firmware or microcode
                           installed on this card, or an empty string if
                           unavailable."
                   ::= { cardTableEntry 6 }

               cardSlotNumber OBJECT-TYPE
                   SYNTAX  INTEGER
                   ACCESS  read-only
                   STATUS  deprecated
                   DESCRIPTION                           "Slot number relative to the containing card or 
                           chassis, or -1 if neither applicable nor 
                           determinable."
                   ::= { cardTableEntry 7 }

               cardContainedByIndex OBJECT-TYPE
                   SYNTAX  INTEGER
                   ACCESS  read-only
                   STATUS  deprecated
                   DESCRIPTION                           "cardIndex of the parent card which
                           directly contains this card, or 0 if
                           contained by the chassis, or -1 if not
                           applicable nor determinable."
                   ::= { cardTableEntry 8 }

               cardOperStatus OBJECT-TYPE
                   SYNTAX  INTEGER {
                          not-specified(1), 
                          up(2),
                          down(3),
                          standby(4)
                      }
                   ACCESS  read-only
                   STATUS  deprecated
                   DESCRIPTION                           "The operational status of the card.
                           cardOperStatus is up when a card is
                           recognized by the device and is enabled for
                           operation. cardOperStatus is down if the
                           card is not recognized by the device, or if
                           it is not enabled for operation.
                           cardOperStatus is standby if the card is
                           enabled and acting as a standby slave"
                   ::= { cardTableEntry 9 }

               cardSlots OBJECT-TYPE
                   SYNTAX  INTEGER
                   ACCESS  read-only
                   STATUS  deprecated
                   DESCRIPTION                           "Number of slots on this card, or 0 if no
                           slots or not applicable, or -1 if not 
			   determinable."
                   ::= { cardTableEntry 10 }

               -- End of table


               chassisSlots OBJECT-TYPE
                   SYNTAX  INTEGER
                   ACCESS  read-only
                   STATUS  deprecated
                   DESCRIPTION                           "Number of slots in this chassis, or -1 of
                           neither applicable nor determinable."
                   ::= { chassis 12 }

               cardIfIndexTable OBJECT-TYPE
                   SYNTAX  SEQUENCE OF CardIfIndexEntry
                   ACCESS  not-accessible
                   STATUS  deprecated
                   DESCRIPTION                            "Chassis card table."
                   ::= { chassis 13 }

               cardIfIndexEntry OBJECT-TYPE
                   SYNTAX CardIfIndexEntry
                   ACCESS  not-accessible
                   STATUS  deprecated
                   DESCRIPTION                            "Chassis card table."
                   INDEX { cardIfIndex }
               ::= { cardIfIndexTable 1 }

               CardIfIndexEntry ::=
                   SEQUENCE {
                       cardIfIndex
                           INTEGER,
                       cardIfSlotNumber
                           INTEGER,
                       cardIfPortNumber
                           INTEGER,
                       cardIfCardIndex
                           INTEGER,
                       cardIfConnectorTypeEnabled
                           INTEGER
                   }

               cardIfIndex OBJECT-TYPE
                   SYNTAX  INTEGER
                   ACCESS  read-only
                   STATUS  deprecated
                   DESCRIPTION                           "matches RFC1213 ifTable IfIndex"
                   ::= { cardIfIndexEntry 1 }

               cardIfSlotNumber OBJECT-TYPE
                   SYNTAX  INTEGER
                   ACCESS  read-only
                   STATUS  deprecated
                   DESCRIPTION                           "Chassis slot number, or -1 if neither
                           applicable nor determinable."
                   ::= { cardIfIndexEntry 2 }

               cardIfPortNumber OBJECT-TYPE
                   SYNTAX  INTEGER
                   ACCESS  read-only
                   STATUS  deprecated
                   DESCRIPTION                           "Chassis port number, unique per port on a 
                            given card if available. If cardIfPortNumber is not
                            applicable to the card, then the object instance
                            won't be populated"
                   ::= { cardIfIndexEntry 3 }

               cardIfCardIndex OBJECT-TYPE
                   SYNTAX  INTEGER
                   ACCESS  read-only
                   STATUS  deprecated
                   DESCRIPTION                           "cardIndex of the card in the Chassis 
                            cardTable which contains this interface, or -1 if
                            not applicable."
                   ::= { cardIfIndexEntry 4 }

               cardIfConnectorTypeEnabled OBJECT-TYPE
                   SYNTAX  INTEGER {
                           not-specified(1), 
                           none (2),
                           rj-45 (3),
                           db-40 (4),
                           db-15 (5),
                           auto-select (6),
                           gbic-sx (7),
                           gbic-lx (8),
                           gbic-lh (9),
                           gbic-cx (10),
                           gbic-zx (11),
                           missing (12),
                           mmf-st (13),
                           mmf-sc (14),
                           rj-11 (15),
                           rj-48s (16),
                           rj-48c (17),
                           db-60 (18),
                           gbic-stack(19),
                           gbic-1000baset(20)
                   }
                   ACCESS  read-only
                   STATUS  deprecated
                   DESCRIPTION                           "Interface connector type currently
                           enabled. Value will be 1 if not known or not
                           used, or 2 if none of this ports' interface
                           connectors are enabled."
                   ::= { cardIfIndexEntry 5 }

	       -- End of table

               chassisPartner OBJECT-TYPE
                   SYNTAX  INTEGER {
			cisco(1)
			,synoptics(2)
			,chipcom(3)
			,cabletron(4)
			,dec(5)
			,ncr(6)
			,usrobotics(7)
			,alcatel(8)
			,nec(9)
			,dsc(10)
			,microcom(11)
			,oki(12)
			,ubn(13)
			,hp(14)
			,samsung(15)
			,mitsubishi(16)
                   }
                   ACCESS  read-only
                   STATUS  deprecated
                   DESCRIPTION                           "Used to determine if this is a partner 
                            variant of a product."
                   ::= { chassis 14 }

               sysUpTimeAtLastChassisChange OBJECT-TYPE
                   SYNTAX  TimeTicks
                   ACCESS  read-only
                   STATUS  deprecated
                   DESCRIPTION                           "Time in seconds/100 from the last cold
                           start to the last change in the chassis'
                           configuration. This value will be updated
                           whenever the chassis experiences a change
                           in the count, type, or slot position of
                           a card in cardTable."
                   ::= { chassis 15 }






               END
