BROADCOM-REF-MIB DEFINITIONS ::= BEGIN

-- DELL FASTPATH Reference MIB
-- Copyright Broadcom Corporation (2001-2007) All rights reserved.

-- This SNMP Management Information Specification
-- embodies Broadcom Corporation confidential and proprietary
-- intellectual property.  Broadcom Corporation retains all title
-- and ownership in the Specification including any revisions.

-- This Specification is supplied "AS IS", Broadcom Corporation
-- makes no warranty, either expressed or implied,
-- as to the use, operation, condition, or performance of the
-- Specification.


IMPORTS
    MODULE-IDENTITY                     FROM SNMPv2-SMI
    TEXTUAL-CONVENTION                  FROM SNMPv2-TC
    dellLanExtension                    FROM Dell-Vendor-MIB
    dellLan                             FROM Dell-Vendor-MIB;

    lvl7 MODULE-IDENTITY
        LAST-UPDATED "200311210000Z" -- 21 Nov 2003 12:00:00 GMT
        ORGANIZATION "Broadcom Corporation"
        CONTACT-INFO
          "                      Customer Support
          Postal:                Broadcom Corporation
                                 100, Perimeter Park Drive
                                 Morrisville, NC 27560
          Tel:                   +1 919 865 2700"
        DESCRIPTION
          ""

        -- Revision history.
        REVISION
          "200311210000Z" -- 21 Nov 2003 12:00:00 GMT
        DESCRIPTION
          "Revisions made for new release."
        REVISION
          "200302061200Z" -- 6 February 2003 12:00:00 GMT
        DESCRIPTION
          "Updated for release"

    ::= {  dellLanExtension 6132 }


-- New definitions
 lvl7Products             OBJECT IDENTIFIER ::= { lvl7 1 }
 fastPath                 OBJECT IDENTIFIER ::= { lvl7Products 1 }

-- These OID to be used in sysObjId to identify the specific switch type:

-- sysObjId for 6224
 dell6224Switch   OBJECT IDENTIFIER ::= { dellLan 3010 }
-- sysObjId for 6248
 dell6248Switch   OBJECT IDENTIFIER ::= { dellLan 3011 }
-- sysObjId for 6224P 
 dell6224PSwitch   OBJECT IDENTIFIER ::= { dellLan 3012 }
-- sysObjId for 6248P
 dell6248PSwitch   OBJECT IDENTIFIER ::= { dellLan 3013 }
-- sysObjId for 6224F
 dell6224FSwitch   OBJECT IDENTIFIER ::= { dellLan 3014 }
-- sysObjId for M6220
 dellM6220Switch  OBJECT IDENTIFIER ::= { dellLan 3015 }


-- New Textual Conventions
AgentPortMask ::= TEXTUAL-CONVENTION
   DISPLAY-HINT "255x"
   STATUS  current
   DESCRIPTION
       "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'

        When setting this value, the system will ignore
        configuration for ports not between the first and last
        valid ports.  Configuration of any port numbers between
        this range that are not valid ports return a failure
        message, but will still apply configuration for valid
        ports."
   SYNTAX  OCTET STRING (SIZE (1..255))


END
